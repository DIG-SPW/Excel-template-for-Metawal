FME workspace Routine_conversion_Excel-XML.fmw

Parameters:
- Dossier_output = $(FME_MF_DIR)template test   # Dossier_output_fichier_xml
- SourceDataset_XLSXR_3 = $(FME_MF_DIR)template test\Fiche_encodage_complete_master_test.xlsm   # Source Microsoft Excel File(s)
- DestDataset_TEXTLINE = $(FME_MF_DIR)template test\fiche_encodage_complet_test.xml   # Destination Text File

Readers:
- XLSXR_1: XLSXR from $(SourceDataset_XLSXR_3)
- XLSXR_2: XLSXR from $(SourceDataset_XLSXR_3)

Writers:
- TEXTLINE_1: TEXTLINE to $(DestDataset_TEXTLINE)

modif_texte_8
    _RESULT = @Value(_result)
    StringReplacer_2_Output -> XMLTemplater_6 [input 4]
    StringReplacer_2_Output -> AttributeCreator_5
INFO_SUPP
    MAXIMUMVALUE = @Value(maximumValue)
    QUANTITATIVERESULTVALUE = @Value(quantitativeResultValue)
    VERSIONYEAR = @Value(versionYear)
    CONSISTENCYDESCRIPTION = @Value(consistencyDescription)
    CREATION_DATE = @Value(creation_date)
    CODESPACE = @Value(CodeSpace)
    REFERENCESYSTEMCODE = @Value(referenceSystemCode)
    CONSISTENCYCODE = @Value(consistencyCode)
    EVALUATIONMETHODTYPE = @Value(evaluationMethodType)
    ABSTRACT = @Value(abstract)
    LEVEL = @Value(level)
    USELIMITATION1 = @Value(useLimitation1)
    CONSISTENCYALTERNATETITLE = @Value(consistencyAlternateTitle)
    USECONSTRAINTS = @Value(useConstraints)
    TITLE = @Value(title)
    HIERARCHYLEVELNAME = @Value(hierarchyLevelName)
    ABSTRACT_BODY = @Value(abstract_body)
    NORTHBOUNDLATITUDE = @Value(northBoundLatitude)
    MAINTENANCENOTE = @Value(maintenanceNote)
    ACRONYM = @Value(acronym)
    ID = @Value(ID)
    CHARACTERSET = @Value(characterSet)
    SOUTHBOUNDLATITUDE = @Value(southBoundLatitude)
    CONFORMANCETITLE = @Value(conformanceTitle)
    CONFORMANCEDATETYPE = @Value(conformanceDateType)
    PARENTIDENTIFIER = @Value(parentIdentifier)
    METADATASTANDARDNAME = @Value(metadataStandardName)
    CONFORMANCEEXPLANATION = @Value(conformanceExplanation)
    SPATIALDESCRIPTION = @Value(spatialDescription)
    USELIMITATION4 = @Value(useLimitation4)
    ENDPOSITION = @Value(endPosition)
    MAINTENANCEANDUPDATEFREQUENCY = @Value(maintenanceAndUpdateFrequency)
    INSPIRECONFORMITY = @Value(INSPIREConformity)
    DATETIME = @Value(dateTime)
    USELIMITATION2 = @Value(useLimitation2)
    REVISION_DATE = @Value(revision_date)
    STATUS = @Value(status)
    FILETYPE = @Value(fileType)
    OTHERCONSTRAINTS1 = @Value(otherConstraints1)
    BEGINPOSITION = @Value(beginPosition)
    FILEDESCRIPTION = @Value(fileDescription)
    METADATASTANDARDVERSION = @Value(metadataStandardVersion)
    USELIMITATION3 = @Value(useLimitation3)
    NAMEOFMEASURE = @Value(nameOfMeasure)
    ALTERNATETITLE = @Value(alternateTitle)
    LANGUAGE = @Value(language)
    CODESPACEREFERENCESYSTEM = @Value(CodeSpaceReferenceSystem)
    CONFORMANCEALTERNATETITLE = @Value(conformanceAlternateTitle)
    LOCALCODE = @Value(localCode)
    CHARACTERSETRESSOURCE = @Value(characterSetRessource)
    PUBLICATION_DATE = @Value(publication_date)
    CONSISTENCYTITLE = @Value(consistencyTitle)
    CONFORMANCEDATE = @Value(conformanceDate)
    MINIMUMVALUE = @Value(minimumValue)
    WESTBOUNDLONGITUDE = @Value(westBoundLongitude)
    CLASSIFICATION = @Value(classification)
    STATEMENTLINEAGE = @Value(statementLineage)
    EASTBOUNDLONGITUDE = @Value(eastBoundLongitude)
    AOI = @Value(AOI)
    VERSION = @Value(Version)
    ACCESSCONSTRAINTS = @Value(accessConstraints)
    METADATA_LANG = @Value(metadata_lang)
    OTHERCONSTRAINTS2 = @Value(otherConstraints2)
    HIERARCHYLEVEL = @Value(hierarchyLevel)
    SPATIALREPRESENTATIONTYPE = @Value(spatialRepresentationType)
    FILENAME = @Value(fileName)
    CONFORMANCEPASS = @Value(conformancePass)
    Output_2 -> modif_texte_17
modif_texte_17
    _RESULT = @Value(_result)
    StringReplacer_2_Output -> XMLTemplater_2 [input 6]
StringReplacer_5
    SRC_ATTRS = _result
    REGEXP = no
    CASE = no
    REPLACE_TEXT = gmd:contact
    NO_MATCH = _FME_NO_OP_
    FIND_TEXT = gmd:pointOfContact
    -> XMLTemplater_2 [input 21]
StringReplacer_6
    SRC_ATTRS = _result
    REGEXP = no
    CASE = no
    REPLACE_TEXT = <
    NO_MATCH = _FME_NO_OP_
    FIND_TEXT = &lt;
    -> StringReplacer_7
StringReplacer_7
    SRC_ATTRS = _result
    REGEXP = no
    CASE = no
    REPLACE_TEXT = >
    NO_MATCH = _FME_NO_OP_
    FIND_TEXT = &gt;
    -> XMLTemplater_2 [input 7]
AttributeCreator_26
    ATTR_LIST = join,1
    -> FeatureMerger_5 [input 2]
Tester_29
    TEST_MODE = Automatic
    TEST_DESCRIPTION = ""
    BOOL_OP = AND
    TEST_CLAUSE:
      TEST spatialRepresentationType NOT_ATTRIBUTE_VALUE_NULL ""
      TEST spatialRepresentationType NOT_ATTRIBUTE_IS_EMPTY ""
      TEST spatialRepresentationType NOT_ATTRIBUTE_IS_MISSING ""
    PASSED -> XMLTemplater_2 [input 12]
Tester_36
    TEST_MODE = Automatic
    TEST_DESCRIPTION = ""
    BOOL_OP = AND
    TEST_CLAUSE:
      TEST status NOT_ATTRIBUTE_VALUE_NULL ""
      TEST status NOT_ATTRIBUTE_IS_EMPTY ""
      TEST status NOT_ATTRIBUTE_IS_MISSING ""
    PASSED -> XMLTemplater_2 [input 8]
StringReplacer_8
    SRC_ATTRS = _result
    REGEXP = no
    CASE = no
    REPLACE_TEXT = <
    NO_MATCH = _FME_NO_OP_
    FIND_TEXT = &lt;
    -> StringReplacer_9
StringReplacer_9
    SRC_ATTRS = _result
    REGEXP = no
    CASE = no
    REPLACE_TEXT = >
    NO_MATCH = _FME_NO_OP_
    FIND_TEXT = &gt;
    -> XMLTemplater_2 [input 19]
DuplicateRemover_14
    KEYATTR = count
    UNIQUE -> XMLTemplater_11 [input 2]
    UNIQUE -> XMLTemplater_11 [input 1]
XMLTemplater_11
    GROUP_BY = count
    RESULT_ATTRIBUTE = _result
    DISTRIBUTION_OFFLINE_QUERY_EXPR:
      <gmd:distributor>
      				<gmd:MD_Distributor>
      			{fme:process-features("DISTRIBUTOR_INFO")}
      			{fme:process-features("OFFLINE")}

      				</gmd:MD_Distributor>
      			</gmd:distributor>
    CONSECUTIVE_GROUPS = No
    DISTRIBUTOR_INFO_QUERY_EXPR = {fme:get-attribute("_result")}
    ROOT_QUERY_EXPR:
      <?xml version="1.0" encoding="UTF-8"?>
      <rw:MD_Metadata xmlns:rw="http://metawal.wallonie.be/schemas/3.0" xmlns:gmd="http://www.isotc211.org/2005/gmd" xmlns:gts="http://www.isotc211.org/2005/gts" xmlns:gco="http://www.isotc211.org/2005/gco" xmlns:gml="http://www.opengis.net/gml" xmlns:geonet="http://www.fao.org/geonetwork" xmlns:xsi="http://www.w3.org/2001/XMLSchema-instance" gco:isoType="gmd:MD_Metadata" xsi:schemaLocation="http://metawal.wallonie.be/schemas/3.0 file:///H:/gimb14/c/c130606/data/schemas/rwschema.xsd">
      {fme:process-features("DISTRIBUTION_OFFLINE")}

      </rw:MD_Metadata>
    VISIBLE_QUERY_VALIDATE = Yes
    OFFLINE_QUERY_EXPR = {fme:get-attribute("_result")}
    OUTPUT_XML_HEADER = Yes
    -> modif_texte_15
modif_texte_15
    _RESULT = @Value(_result)
    StringReplacer_2_Output -> StringReplacer_10
StringReplacer_10
    SRC_ATTRS = _result
    REGEXP = no
    CASE = no
    REPLACE_TEXT = <
    NO_MATCH = _FME_NO_OP_
    FIND_TEXT = &lt;
    -> StringReplacer_11
StringReplacer_11
    SRC_ATTRS = _result
    REGEXP = no
    CASE = no
    REPLACE_TEXT = >
    NO_MATCH = _FME_NO_OP_
    FIND_TEXT = &gt;
    -> XMLTemplater_2 [input 19]
DuplicateRemover_9
    KEYATTR = identifiant
    UNIQUE -> Tester_34
AttributeCreator_24
    ATTR_LIST = identifiant,81
    -> XMLTemplater_2 [input 17]
    -> DuplicateRemover_17
DuplicateRemover_17
    KEYATTR = identifiant
    UNIQUE -> AttributeCreator_23
    UNIQUE -> XMLTemplater_2 [input 4]
AttributeCreator_23
    ATTR_LIST = identifiant,59
    -> DuplicateRemover_18
DuplicateRemover_18
    KEYATTR = identifiant
    UNIQUE -> XMLTemplater_2 [input 11]
DuplicateRemover_11
    KEYATTR = identifiant

Bookmark: Point de contact
synthese/pt_contact (reader XLSXR_1)
    attributes: Role char(174), organisationName char(27), electronicMailAddress char(31), individualName string, positionName string, voice string, deliveryPoint string, city char(13), postalCode string, country string, linkage char(36), protocole char(23), name char(26), description string, function char(7)
    -> AttributeValueMapper_4
AttributeValueMapper_4
    DIRECTION = Forward (Source To Destination)
    VAL_ATTR = protocole
    LUT = Adresse Internet (http),WWW:LINK-1.0-http--link,Fichier à télécharger (http),WWW:DOWNLOAD-1.0-http--download,Fil RSS (http),WWW:LINK-1.0-http--rss,Unknown Service Type,UKST
    SRC = protocole
    -> AttributeSplitter_3
AttributeSplitter_3
    LIST_NAME = _list
    ATTR_NAME = Role
    DELIMITER = ;
    TRIM_OPTION = Both
    DROP_EMPTY_PARTS = No
    -> ListExploder_3
ListExploder_3
    INDEX_ATTR = _element_index
    MODE = List Elements and Original Attributes
    LIST_ATTR = _list{}
    LIST_FOUND -> AttributeCopier
AttributeCopier
    ATTR_LIST = _list,Role_type,""
    -> AttributeRenamer
AttributeRenamer
    ATTR_LIST = _list,Role,""
    -> AttributeValueMapper
AttributeValueMapper
    DIRECTION = Forward (Source To Destination)
    VAL_ATTR = Role
    LUT = A l'origine de,originator,Point de contact (fiche),pointOfContact,Point de contact (ressource),pointOfContact,Point de recherche,principalInvestigator,Auteur,author,Distributeur,distributor,Editeur,publisher,Exécutant,processor,Fournisseur,resourceProvider,Gestionnaire,custodian,Propriétaire,owner,Utilisateur,user
    SRC = Role
    -> Tester_2
Tester_2
    TEST_MODE = Automatic
    TEST_DESCRIPTION = ""
    BOOL_OP = OR
    TEST_CLAUSE:
      TEST @Value(Role) = Role
      TEST Role ATTRIBUTE_IS_EMPTY ""
    FAILED -> Tester_41
Tester_41
    TEST_MODE = Automatic
    TEST_DESCRIPTION = ""
    BOOL_OP = AND
    TEST_CLAUSE:
      TEST organisationName NOT_ATTRIBUTE_VALUE_NULL ""
      TEST organisationName NOT_ATTRIBUTE_IS_EMPTY ""
      TEST organisationName NOT_ATTRIBUTE_IS_MISSING ""
    PASSED -> TestFilter
TestFilter
    TEST_LIST = BOOL_OP,OR,COMPOSITE_TEST,<Unused>,TEST_CLAUSE,"TEST @Value(Role_type) = Point de contact (fiche)",Point de contact (fiche),BOOL_OP,OR,COMPOSITE_TEST,<Unused>,TEST_CLAUSE,"TEST @Value(Role_type) = Distributeur",Distributeur
    DEFAULT_VALUE = Autre
    Point de contact (fiche) -> AttributeCreator_9
    Distributeur -> FeatureMerger_3 [input 2]
    Distributeur -> FeatureMerger_4 [input 2]
    Autre -> Counter
AttributeCreator_9
    ATTR_LIST = join,1
    -> FeatureMerger [input 1]
Counter
    SCOPE = Global
    START = 0
    DOMAIN = counter
    CNT_ATTR = _count
    -> BulkAttributeRenamer
BulkAttributeRenamer
    REPLACE_STR = Contactsupp_
    ATTRCHOICE = All Attributes
    PATTERN_ACTION_DISP = Add String Prefix
    -> CONTACTS
CONTACTS
    CONTACTSUPP_VOICE = @Value(Contactsupp_voice)
    CONTACTSUPP_CITY = @Value(Contactsupp_city)
    CONTACTSUPP_COUNTRY = @Value(Contactsupp_country)
    CONTACTSUPP_INDIVIDUALNAME = @Value(Contactsupp_individualName)
    CONTACTSUPP_LINKAGE = @Value(Contactsupp_linkage)
    CONTACTSUPP_DELIVERYPOINT = @Value(Contactsupp_deliveryPoint)
    CONTACTSUPP_FUNCTION = @Value(Contactsupp_function)
    CONTACTSUPP_ELECTRONICMAILADDRESS = @Value(Contactsupp_electronicMailAddress)
    CONTACTSUPP_ROLE = @Value(Contactsupp_Role)
    CONTACTSUPP_NAME = @Value(Contactsupp_name)
    CONTACTSUPP_POSITIONNAME = @Value(Contactsupp_positionName)
    CONTACTSUPP_ROLE_TYPE = @Value(Contactsupp_Role_type)
    CONTACTSUPP_ORGANISATIONNAME = @Value(Contactsupp_organisationName)
    CONTACTSUPP__ELEMENT_INDEX = @Value(Contactsupp__element_index)
    CONTACTSUPP_DESCRIPTION = @Value(Contactsupp_description)
    CONTACTSUPP_POSTALCODE = @Value(Contactsupp_postalCode)
    CONTACTSUPP__COUNT = @Value(Contactsupp__count)
    CONTACTSUPP_PROTOCOLE = @Value(Contactsupp_protocole)
    modif_texte_8_StringReplacer_2_Output -> Tester_40
Tester_40
    TEST_MODE = Automatic
    TEST_DESCRIPTION = ""
    BOOL_OP = OR
    TEST_CLAUSE = TEST @Value(Contactsupp_Role) != owner
    PASSED -> modif_texte_8
AttributeCreator_25
    ATTR_LIST = organisationName_owner,Région wallonne,electronicMailAddress_owner,helpdesk.carto@spw.wallonie.be,linkage_owner,http://geoportail.wallonie.be,protocole_owner,WWW:LINK-1.0-http--link,name_owner,Géoportail de la Wallonie,Role_owner,owner,Fonction_owner,information
    -> XMLTemplater_3 [input 1]
    -> XMLTemplater_2 [input 1]
FeatureMerger
    PROCESS_DUPS = No
    MERGE_TYPE = Attributes Only
    SUPPLIERS_FIRST = No
    JOIN_KEYS = @Value(join) @Value(join) AUTO
    SUPPLIER_PREFIX_DUMMY = YES
    MERGED -> Counter_2
Counter_2
    SCOPE = Global
    START = 0
    DOMAIN = counter
    CNT_ATTR = _count
    -> BulkAttributeRenamer_9
BulkAttributeRenamer_9
    REPLACE_STR = Contactsupp_
    ATTRCHOICE = All Attributes
    PATTERN_ACTION_DISP = Add String Prefix
    -> CONTACTS_2
CONTACTS_2
    CONTACTSUPP_VOICE = @Value(Contactsupp_voice)
    CONTACTSUPP_CITY = @Value(Contactsupp_city)
    CONTACTSUPP_COUNTRY = @Value(Contactsupp_country)
    CONTACTSUPP_INDIVIDUALNAME = @Value(Contactsupp_individualName)
    CONTACTSUPP_LINKAGE = @Value(Contactsupp_linkage)
    CONTACTSUPP_DELIVERYPOINT = @Value(Contactsupp_deliveryPoint)
    CONTACTSUPP_FUNCTION = @Value(Contactsupp_function)
    CONTACTSUPP_ELECTRONICMAILADDRESS = @Value(Contactsupp_electronicMailAddress)
    CONTACTSUPP_ROLE = @Value(Contactsupp_Role)
    CONTACTSUPP_NAME = @Value(Contactsupp_name)
    CONTACTSUPP_POSITIONNAME = @Value(Contactsupp_positionName)
    CONTACTSUPP_ROLE_TYPE = @Value(Contactsupp_Role_type)
    CONTACTSUPP_ORGANISATIONNAME = @Value(Contactsupp_organisationName)
    CONTACTSUPP__ELEMENT_INDEX = @Value(Contactsupp__element_index)
    CONTACTSUPP_DESCRIPTION = @Value(Contactsupp_description)
    CONTACTSUPP_POSTALCODE = @Value(Contactsupp_postalCode)
    CONTACTSUPP__COUNT = @Value(Contactsupp__count)
    CONTACTSUPP_PROTOCOLE = @Value(Contactsupp_protocole)
    modif_texte_8_StringReplacer_2_Output -> modif_texte_9
modif_texte_9
    _RESULT = @Value(_result)
    StringReplacer_2_Output -> StringReplacer_5
AttributeKeeper_8
    KEEP_ATTRS = conformanceExplanation
    -> AttributeCreator_26

Bookmark: INSPIRE
synthese/INSPIRE (reader XLSXR_1)
    attributes: Nom char(79), Concernée par le théme char(3), Conforme au thème char(3), Traduction char(118), Date date
    -> AttributeCreator_12
    -> Tester_14
AttributeCreator_12
    ATTR_LIST = join,1
    -> FeatureMerger_2 [input 1]
Tester_14
    TEST_MODE = Automatic
    TEST_DESCRIPTION = ""
    BOOL_OP = OR
    TEST_CLAUSE = TEST @Value(Concernée par le théme) = Yes
    PASSED -> AttributeRenamer_2
    PASSED -> Tester
AttributeRenamer_2
    ATTR_LIST = Nom,Valeur,""
    -> AttributeCreator_2
AttributeCreator_2
    ATTR_LIST = Nom,GEMET - INSPIRE themes, version 1.0,Date,20080601,Type de date,publication
    -> DateFormatter_2
FeatureMerger_2
    PROCESS_DUPS = No
    MERGE_TYPE = Attributes Only
    SUPPLIERS_FIRST = No
    JOIN_KEYS = @Value(join) @Value(join) AUTO
    SUPPLIER_PREFIX_DUMMY = YES
    MERGED -> Tester_15
Tester_15
    TEST_MODE = Automatic
    TEST_DESCRIPTION = ""
    BOOL_OP = OR
    TEST_CLAUSE = TEST @Value(Valeur) = Yes
    PASSED -> Tester_44
Tester_44
    TEST_MODE = Automatic
    TEST_DESCRIPTION = ""
    BOOL_OP = OR
    TEST_CLAUSE = TEST @Value(Concernée par le théme) = Yes
    PASSED -> DateFormatter_4
DateFormatter_4
    DATE_ATTR = Date
    FMT = ISO Date (%Y-%m-%d)
    SRCFMT = Unknown - Automatic Detection
    INVALID_DATE_VALUE = _FME_NO_OP_
    -> AttributeValueMapper_3
AttributeValueMapper_3
    DIRECTION = Forward (Source To Destination)
    VAL_ATTR = Conforme au thème
    LUT = Yes,true,No,false
    SRC = Conforme au thème
    -> BulkAttributeRenamer_11
BulkAttributeRenamer_11
    REPLACE_STR = inspire_
    ATTRCHOICE = All Attributes
    PATTERN_ACTION_DISP = Add String Prefix
    -> XMLTemplater_2 [input 20]

Bookmark: Systeme_coordonnées_Inspire1
Tester
    TEST_MODE = Automatic
    TEST_DESCRIPTION = ""
    BOOL_OP = OR
    TEST_CLAUSE = TEST @Value(Date) = 20140417
    PASSED -> DuplicateRemover
DuplicateRemover
    KEYATTR = Date
    UNIQUE -> XMLTemplater_2 [input 2]

Bookmark: EPSG
synthese/EPSG (reader XLSXR_1)
    attributes: Type char(5), Valeur char(4)
    -> Tester_39
Tester_39
    TEST_MODE = Automatic
    TEST_DESCRIPTION = ""
    BOOL_OP = OR
    TEST_CLAUSE = TEST @Value(Valeur) = Yes
    PASSED -> XMLTemplater_2 [input 3]

Bookmark: Synthese
synthese/principal (reader XLSXR_1)
    attributes: ID number(2,0), parentIdentifier string, hierarchyLevel string, hierarchyLevelName string, title string, alternateTitle string, acronym string, versionYear string, AOI string, creation_date string, publication_date string, revision_date string, localCode char(3), abstract string, abstract_body string, status string, maintenanceAndUpdateFrequency string, maintenanceNote string, fileName string, fileDescription string, fileType string, spatialRepresentationType string, beginPosition string, endPosition string, statementLineage string, INSPIREConformity string, nameOfMeasure char(20), consistencyTitle char(8), consistencyAlternateTitle string, consistencyCode string,
      consistencyDescription string, evaluationMethodType string, dateTime string, conformanceTitle char(250), conformanceAlternateTitle string, conformanceDate char(11), conformanceDateType char(12), conformanceExplanation char(47), conformancePass char(12), quantitativeResultValue string, characterSet char(5), metadataStandardName char(10), metadataStandardVersion char(16), CodeSpace char(46), metadata_lang char(4), referenceSystemCode number(6,0), CodeSpaceReferenceSystem char(21), Version char(6), language char(4), characterSetRessource char(5), spatialDescription string, westBoundLongitude number(4,2), eastBoundLongitude number(3,1), southBoundLatitude number(5,2), northBoundLatitude number(5,2), minimumValue char(4), maximumValue char(5), level string, classification string, useLimitation1 string,
      useLimitation2 string, accessConstraints string, useConstraints string, otherConstraints1 string, otherConstraints2 string, useLimitation3 string, useLimitation4 string
    -> TimeStamper
    -> AttributeKeeper_2
    -> AttributeKeeper
    -> AttributeKeeper_3
    -> XMLTemplater_4 [input 1]
    -> Tester_25
    -> Tester_26
    -> Tester_27
    -> Tester_28
    -> Tester_29
    -> Tester_30
    -> Tester_31
    -> Tester_36
    -> Tester_37
    -> Tester_38
    -> Tester_24
    -> INFO_SUPP
    -> Parent_identifier
    -> AttributeKeeper_8
AttributeKeeper_2
    KEEP_ATTRS = alternateTitle
    -> AttributeSplitter_4
AttributeSplitter_4
    LIST_NAME = _list
    ATTR_NAME = alternateTitle
    DELIMITER = ;
    TRIM_OPTION = Both
    DROP_EMPTY_PARTS = No
    -> ListExploder_4
ListExploder_4
    INDEX_ATTR = _element_index
    MODE = List Elements and Original Attributes
    LIST_ATTR = _list{}
    LIST_FOUND -> AttributeCopier_2
AttributeCopier_2
    ATTR_LIST = _list,alternateTitle,""
    -> AttributeCreator_16
AttributeKeeper_3
    KEEP_ATTRS = acronym
    -> Tester_23
Tester_23
    TEST_MODE = Automatic
    TEST_DESCRIPTION = ""
    BOOL_OP = AND
    TEST_CLAUSE:
      TEST acronym NOT_ATTRIBUTE_VALUE_NULL ""
      TEST acronym NOT_ATTRIBUTE_IS_EMPTY ""
      TEST acronym NOT_ATTRIBUTE_IS_MISSING ""
    PASSED -> AttributeRenamer_5
AttributeRenamer_5
    ATTR_LIST = acronym,alternateTitle,""
    -> AttributeCreator_16
AttributeCreator_16
    ATTR_LIST = identifiant,23
    -> BulkAttributeRenamer_10
BulkAttributeRenamer_10
    REPLACE_STR = AlternateTitle_
    ATTRCHOICE = All Attributes
    PATTERN_ACTION_DISP = Add String Prefix
    -> XMLTemplater_4 [input 4]
TimeStamper
    FMT = XML DateTime (^Y-^m-^dT^H:^M:^S)
    TIME_ATTR = _timestamp
    -> DateFormatter
DateFormatter
    DATE_ATTR = creation_date,publication_date,revision_date,beginPosition,endPosition,conformanceDate
    FMT = ISO Date (%Y-%m-%d)
    SRCFMT = Unknown - Automatic Detection
    INVALID_DATE_VALUE = _FME_NO_OP_
    -> DateFormatter_3
DateFormatter_3
    DATE_ATTR = dateTime
    FMT = ISO DateTime (%Y-%m-%dT%H:%M:%S)
    SRCFMT = Unknown - Automatic Detection
    INVALID_DATE_VALUE = _FME_NO_OP_
    -> AttributeCreator_3
AttributeCreator_3
    ATTR_LIST:
      abstract,@Value(abstract)
      @Value(abstract_body)
    -> Tester_10
Tester_10
    TEST_MODE = Automatic
    TEST_DESCRIPTION = ""
    BOOL_OP = AND
    TEST_CLAUSE:
      TEST acronym NOT_ATTRIBUTE_VALUE_NULL ""
      TEST acronym NOT_ATTRIBUTE_IS_EMPTY ""
      TEST acronym NOT_ATTRIBUTE_IS_MISSING ""
    PASSED -> AttributeCreator_4
    FAILED -> Tester_11
AttributeCreator_4
    ATTR_LIST = "acronym, (@Value(acronym)) "
    -> Tester_12
Tester_12
    TEST_MODE = Automatic
    TEST_DESCRIPTION = ""
    BOOL_OP = AND
    TEST_CLAUSE:
      TEST versionYear NOT_ATTRIBUTE_IS_MISSING ""
      TEST versionYear NOT_ATTRIBUTE_VALUE_NULL ""
      TEST versionYear NOT_ATTRIBUTE_IS_EMPTY ""
    PASSED -> AttributeCreator_6
    FAILED -> AttributeCreator_7
AttributeCreator_6
    ATTR_LIST = versionYear,_@Value(versionYear)
    -> AttributeCreator_7
AttributeCreator_7
    ATTR_LIST = title,@Value(title)@Value(AOI)@Value(acronym)@Value(versionYear),organisationName_owner,Service Public de Wallonie,electronicMailAddress_owner,helpdesk.carto@spw.wallonie.be,linkage_owner,http://www.cartographie.wallonie.be,protocole_owner,WWW:LINK-1.0-http--link,name_owner,Géoportail de la Wallonie,Role_owner,owner
    -> Tester_11
Tester_11
    TEST_MODE = Automatic
    TEST_DESCRIPTION = ""
    BOOL_OP = OR
    TEST_CLAUSE = TEST 0 = 0
    PASSED -> AttributeCreator_25
AttributeKeeper
    KEEP_ATTRS = metadata_lang
    -> AttributeCreator_8
AttributeCreator_8
    ATTR_LIST = join,1
    -> FeatureMerger [input 2]

Bookmark: Etendue temporelle
Tester_27
    TEST_MODE = Automatic
    TEST_DESCRIPTION = ""
    BOOL_OP = AND
    TEST_CLAUSE:
      TEST beginPosition NOT_ATTRIBUTE_VALUE_NULL ""
      TEST beginPosition NOT_ATTRIBUTE_IS_EMPTY ""
      TEST beginPosition NOT_ATTRIBUTE_IS_MISSING ""
    PASSED -> DuplicateRemover_10
    PASSED -> XMLTemplater_5 [input 2]
Tester_28
    TEST_MODE = Automatic
    TEST_DESCRIPTION = ""
    BOOL_OP = AND
    TEST_CLAUSE:
      TEST endPosition NOT_ATTRIBUTE_VALUE_NULL ""
      TEST endPosition NOT_ATTRIBUTE_IS_EMPTY ""
      TEST endPosition NOT_ATTRIBUTE_IS_MISSING ""
    PASSED -> DuplicateRemover_10
    PASSED -> XMLTemplater_5 [input 3]
DuplicateRemover_10
    KEYATTR = ID
    UNIQUE -> XMLTemplater_5 [input 1]
XMLTemplater_5
    RESULT_ATTRIBUTE = _result
    END_QUERY_EXPR = <gml:endPosition>{fme:get-attribute("endPosition")}</gml:endPosition>
    BEGIN_QUERY_EXPR = <gml:beginPosition>{fme:get-attribute("beginPosition")}</gml:beginPosition>
    ROOT_QUERY_EXPR:
           <?xml version="1.0" encoding="UTF-8"?>
      <rw:MD_Metadata xmlns:rw="http://metawal.wallonie.be/schemas/3.0" xmlns:gmd="http://www.isotc211.org/2005/gmd" xmlns:gts="http://www.isotc211.org/2005/gts" xmlns:gco="http://www.isotc211.org/2005/gco" xmlns:gml="http://www.opengis.net/gml" xmlns:geonet="http://www.fao.org/geonetwork" xmlns:xsi="http://www.w3.org/2001/XMLSchema-instance" gco:isoType="gmd:MD_Metadata" xsi:schemaLocation="http://metawal.wallonie.be/schemas/3.0 file:///H:/gimb14/c/c130606/data/schemas/rwschema.xsd">
          <gmd:extent>
              <gmd:EX_Extent>

                  <gmd:temporalElement>

                      <gmd:EX_TemporalExtent>

                          <gmd:extent>

                             <gml:TimePeriod gml:id="T1">

                               {fme:process-features("BEGIN")}
                               {fme:process-features("END")}


                              </gml:TimePeriod>

                          </gmd:extent>

                      </gmd:EX_TemporalExtent>

                  </gmd:temporalElement>

              </gmd:EX_Extent>

          </gmd:extent>

      </rw:MD_Metadata>
    VISIBLE_QUERY_VALIDATE = Yes
    OUTPUT_XML_HEADER = Yes
    -> modif_texte_4
modif_texte_4
    _RESULT = @Value(_result)
    StringReplacer_2_Output -> XMLTemplater_2 [input 13]

Bookmark: Uselimitation_classification
Tester_37
    TEST_MODE = Automatic
    TEST_DESCRIPTION = ""
    BOOL_OP = AND
    TEST_CLAUSE:
      TEST classification NOT_ATTRIBUTE_VALUE_NULL ""
      TEST classification NOT_ATTRIBUTE_IS_EMPTY ""
      TEST classification NOT_ATTRIBUTE_IS_MISSING ""
    PASSED -> DuplicateRemover_16
    PASSED -> XMLTemplater_9 [input 3]
Tester_38
    TEST_MODE = Automatic
    TEST_DESCRIPTION = ""
    BOOL_OP = AND
    TEST_CLAUSE:
      TEST useLimitation1 NOT_ATTRIBUTE_VALUE_NULL ""
      TEST useLimitation1 NOT_ATTRIBUTE_IS_EMPTY ""
      TEST useLimitation1 NOT_ATTRIBUTE_IS_MISSING ""
    PASSED -> DuplicateRemover_16
    PASSED -> XMLTemplater_9 [input 2]
DuplicateRemover_16
    KEYATTR = ID
    UNIQUE -> XMLTemplater_9 [input 1]
XMLTemplater_9
    RESULT_ATTRIBUTE = _result
    CLASSIFICATION_QUERY_EXPR:
        <gmd:classification>
      				<gmd:MD_ClassificationCode codeList="http://standards.iso.org/ittf/PubliclyAvailableStandards/ISO_19139_Schemas/resources/Codelist/ML_gmxCodelists.xml#MD_ClassificationCode" codeListValue="{fme:get-attribute("classification")}"/>
      </gmd:classification>
    ROOT_QUERY_EXPR:
           <?xml version="1.0" encoding="UTF-8"?>
      <rw:MD_Metadata xmlns:rw="http://metawal.wallonie.be/schemas/3.0" xmlns:gmd="http://www.isotc211.org/2005/gmd" xmlns:gts="http://www.isotc211.org/2005/gts" xmlns:gco="http://www.isotc211.org/2005/gco" xmlns:gml="http://www.opengis.net/gml" xmlns:geonet="http://www.fao.org/geonetwork" xmlns:xsi="http://www.w3.org/2001/XMLSchema-instance" gco:isoType="gmd:MD_Metadata" xsi:schemaLocation="http://metawal.wallonie.be/schemas/3.0 file:///H:/gimb14/c/c130606/data/schemas/rwschema.xsd">
      <gmd:resourceConstraints>

      		<gmd:MD_SecurityConstraints>
      			{fme:process-features("USELIMITATION")}
                  {fme:process-features("CLASSIFICATION")}

              </gmd:MD_SecurityConstraints>
      	</gmd:resourceConstraints>

      </rw:MD_Metadata>
    VISIBLE_QUERY_VALIDATE = Yes
    USELIMITATION_QUERY_EXPR:
      <gmd:useLimitation>
      				<gco:CharacterString>{fme:get-attribute("useLimitation1")}</gco:CharacterString>
      </gmd:useLimitation>
    OUTPUT_XML_HEADER = Yes
    -> modif_texte_11
modif_texte_11
    _RESULT = @Value(_result)
    StringReplacer_2_Output -> StringReplacer_6

Bookmark: Contact Maintenance et update + Note
Tester_30
    TEST_MODE = Automatic
    TEST_DESCRIPTION = ""
    BOOL_OP = AND
    TEST_CLAUSE:
      TEST maintenanceAndUpdateFrequency NOT_ATTRIBUTE_VALUE_NULL ""
      TEST maintenanceAndUpdateFrequency NOT_ATTRIBUTE_IS_EMPTY ""
      TEST maintenanceAndUpdateFrequency NOT_ATTRIBUTE_IS_MISSING ""
    PASSED -> XMLTemplater_6 [input 2]
    PASSED -> AttributeCreator_5
    PASSED -> AttributeCreator_18
Tester_31
    TEST_MODE = Automatic
    TEST_DESCRIPTION = ""
    BOOL_OP = AND
    TEST_CLAUSE:
      TEST maintenanceNote NOT_ATTRIBUTE_VALUE_NULL ""
      TEST maintenanceNote NOT_ATTRIBUTE_IS_EMPTY ""
      TEST maintenanceNote NOT_ATTRIBUTE_IS_MISSING ""
    PASSED -> XMLTemplater_6 [input 5]
    PASSED -> AttributeCreator_5
    PASSED -> AttributeCreator_18
AttributeCreator_5
    ATTR_LIST = ID,1
    -> DuplicateRemover_12
DuplicateRemover_12
    KEYATTR = ID
    UNIQUE -> XMLTemplater_6 [input 1]
AttributeCreator_18
    ATTR_LIST = ID,1
    -> DuplicateRemover_20
DuplicateRemover_20
    KEYATTR = ID
    UNIQUE -> XMLTemplater_6 [input 3]
XMLTemplater_6
    MAINTENANCE_INFO_QUERY_EXPR:
        <gmd:resourceMaintenance>
      				<gmd:MD_MaintenanceInformation>
      		{fme:process-features("MAINTENANCEUPDATE")}
           {fme:process-features("MAINTENANCENOTE")}

      				</gmd:MD_MaintenanceInformation>
      			</gmd:resourceMaintenance>
    RESULT_ATTRIBUTE = _result
    CONTACT_QUERY_EXPR = {fme:get-attribute("_result")}
    ROOT_QUERY_EXPR:
      <?xml version="1.0" encoding="UTF-8"?>
      <rw:MD_Metadata xmlns:rw="http://metawal.wallonie.be/schemas/3.0" xmlns:gmd="http://www.isotc211.org/2005/gmd" xmlns:gts="http://www.isotc211.org/2005/gts" xmlns:gco="http://www.isotc211.org/2005/gco" xmlns:gml="http://www.opengis.net/gml" xmlns:geonet="http://www.fao.org/geonetwork" xmlns:xsi="http://www.w3.org/2001/XMLSchema-instance" gco:isoType="gmd:MD_Metadata" xsi:schemaLocation="http://metawal.wallonie.be/schemas/3.0 file:///H:/gimb14/c/c130606/data/schemas/rwschema.xsd">

          {fme:process-features("CONTACT")}

      {fme:process-features("MAINTENANCE_INFO")}


      </rw:MD_Metadata>
    MAINTENANCEUPDATE_QUERY_EXPR:
      <gmd:maintenanceAndUpdateFrequency>
      						<gmd:MD_MaintenanceFrequencyCode codeList="http://standards.iso.org/ittf/PubliclyAvailableStandards/ISO_19139_Schemas/resources/Codelist/ML_gmxCodelists.xml#MD_MaintenanceFrequencyCode" codeListValue="{fme:get-attribute("maintenanceAndUpdateFrequency")}"/>
      					</gmd:maintenanceAndUpdateFrequency>
    VISIBLE_QUERY_VALIDATE = Yes
    MAINTENANCENOTE_QUERY_EXPR:
      	<gmd:maintenanceNote>
                          <gco:CharacterString>{fme:get-attribute("maintenanceNote")}</gco:CharacterString>
                          </gmd:maintenanceNote>
    OUTPUT_XML_HEADER = Yes
    -> modif_texte_5
modif_texte_5
    _RESULT = @Value(_result)
    StringReplacer_2_Output -> StringReplacer_3
StringReplacer_3
    SRC_ATTRS = _result
    REGEXP = no
    CASE = no
    REPLACE_TEXT = <
    NO_MATCH = _FME_NO_OP_
    FIND_TEXT = &lt;
    -> StringReplacer_4
StringReplacer_4
    SRC_ATTRS = _result
    REGEXP = no
    CASE = no
    REPLACE_TEXT = >
    NO_MATCH = _FME_NO_OP_
    FIND_TEXT = &gt;
    -> XMLTemplater_2 [input 9]

Bookmark: Alternate title Date création publication révision Local Code
Tester_24
    TEST_MODE = Automatic
    TEST_DESCRIPTION = ""
    BOOL_OP = AND
    TEST_CLAUSE:
      TEST creation_date NOT_ATTRIBUTE_VALUE_NULL ""
      TEST creation_date NOT_ATTRIBUTE_IS_EMPTY ""
      TEST creation_date NOT_ATTRIBUTE_IS_MISSING ""
    PASSED -> XMLTemplater_4 [input 2]
Tester_25
    TEST_MODE = Automatic
    TEST_DESCRIPTION = ""
    BOOL_OP = AND
    TEST_CLAUSE:
      TEST publication_date NOT_ATTRIBUTE_VALUE_NULL ""
      TEST publication_date NOT_ATTRIBUTE_IS_EMPTY ""
      TEST publication_date NOT_ATTRIBUTE_IS_MISSING ""
    PASSED -> XMLTemplater_4 [input 5]
Tester_26
    TEST_MODE = Automatic
    TEST_DESCRIPTION = ""
    BOOL_OP = AND
    TEST_CLAUSE:
      TEST revision_date NOT_ATTRIBUTE_VALUE_NULL ""
      TEST revision_date NOT_ATTRIBUTE_IS_EMPTY ""
      TEST revision_date NOT_ATTRIBUTE_IS_MISSING ""
    PASSED -> XMLTemplater_4 [input 6]
XMLTemplater_4
    RESULT_ATTRIBUTE = _result
    CREATION_DATE_QUERY_EXPR:
      	<gmd:date>
      				<gmd:CI_Date>
                          <gmd:date>
      								<gco:Date>{fme:get-attribute("creation_date")}</gco:Date>
      							</gmd:date>
      							<gmd:dateType>
      								<gmd:CI_DateTypeCode codeListValue="creation" codeList="http://standards.iso.org/ittf/PubliclyAvailableStandards/ISO_19139_Schemas/resources/Codelist/ML_gmxCodelists.xml#CI_DateTypeCode"/>
      							</gmd:dateType>
      						</gmd:CI_Date>
          	</gmd:date>
    PUBLICATION_DATE_QUERY_EXPR:
      	<gmd:date>
      <gmd:CI_Date>
      							<gmd:date>
      								<gco:Date>{fme:get-attribute("publication_date")}</gco:Date>
      							</gmd:date>
      							<gmd:dateType>
      								<gmd:CI_DateTypeCode codeList="http://standards.iso.org/ittf/PubliclyAvailableStandards/ISO_19139_Schemas/resources/Codelist/ML_gmxCodelists.xml#CI_DateTypeCode" codeListValue="publication"/>
      							</gmd:dateType>
      						</gmd:CI_Date>
       	</gmd:date>
    ALTERNATE_TITLE_INFO_QUERY_EXPR:
       <gmd:alternateTitle>
      <gco:CharacterString>{fme:get-attribute("AlternateTitle_alternateTitle")}</gco:CharacterString>
      </gmd:alternateTitle>
    LOCALCODDE_VALUE_QUERY_EXPR:
          <gmd:identifier>
          <gmd:MD_Identifier>
                  <gmd:code>
                    <gco:CharacterString>{fme:get-attribute("local_codeValeur1")}</gco:CharacterString>
                  </gmd:code>
         </gmd:MD_Identifier>
           </gmd:identifier>
    ROOT_QUERY_EXPR:
      <?xml version="1.0" encoding="UTF-8"?>
      <rw:MD_Metadata xmlns:rw="http://metawal.wallonie.be/schemas/3.0" xmlns:gmd="http://www.isotc211.org/2005/gmd" xmlns:gts="http://www.isotc211.org/2005/gts" xmlns:gco="http://www.isotc211.org/2005/gco" xmlns:gml="http://www.opengis.net/gml" xmlns:geonet="http://www.fao.org/geonetwork" xmlns:xsi="http://www.w3.org/2001/XMLSchema-instance" gco:isoType="gmd:MD_Metadata" xsi:schemaLocation="http://metawal.wallonie.be/schemas/3.0 file:///H:/gimb14/c/c130606/data/schemas/rwschema.xsd">
      {fme:process-features("ALTERNATE_TITLE_INFO")}
      {fme:process-features("CREATION_DATE")}
      {fme:process-features("PUBLICATION_DATE")}
      {fme:process-features("REVISION_DATE")}
      {fme:process-features("LOCALCODDE_VALUE")}
      </rw:MD_Metadata>
    VISIBLE_QUERY_VALIDATE = Yes
    REVISION_DATE_QUERY_EXPR:
      	<gmd:date>
      	<gmd:CI_Date>
      							<gmd:date>
      								<gco:Date>{fme:get-attribute("revision_date")}</gco:Date>
      							</gmd:date>
      							<gmd:dateType>
      								<gmd:CI_DateTypeCode codeList="http://standards.iso.org/ittf/PubliclyAvailableStandards/ISO_19139_Schemas/resources/Codelist/ML_gmxCodelists.xml#CI_DateTypeCode" codeListValue="revision"/>
      							</gmd:dateType>
      						</gmd:CI_Date>
          </gmd:date>
    OUTPUT_XML_HEADER = Yes
    -> modif_texte_3
modif_texte_3
    _RESULT = @Value(_result)
    StringReplacer_2_Output -> XMLTemplater_2 [input 14]

Bookmark: Keywords
Parent_identifier: Tester
    TEST_MODE = Automatic
    TEST_DESCRIPTION = ""
    BOOL_OP = AND
    TEST_CLAUSE:
      TEST parentIdentifier NOT_ATTRIBUTE_VALUE_NULL ""
      TEST parentIdentifier NOT_ATTRIBUTE_IS_EMPTY ""
      TEST parentIdentifier NOT_ATTRIBUTE_IS_MISSING ""
    PASSED -> XMLTemplater_2 [input 5]
synthese/keywords2 (reader XLSXR_1)
    attributes: Keywords char(16), Nom char(41), Valeur string, Date char(11), Type de date char(12)
    -> Tester_3
Tester_3
    TEST_MODE = Automatic
    TEST_DESCRIPTION = ""
    BOOL_OP = OR
    TEST_CLAUSE:
      TEST @Value(Nom) = Nom
      TEST Valeur ATTRIBUTE_IS_MISSING ""
      TEST Valeur ATTRIBUTE_IS_EMPTY ""
    FAILED -> AttributeSplitter_5
AttributeSplitter_5
    LIST_NAME = _list
    ATTR_NAME = Valeur
    DELIMITER = ;
    TRIM_OPTION = Both
    DROP_EMPTY_PARTS = No
    -> ListExploder_5
ListExploder_5
    INDEX_ATTR = _element_index
    MODE = List Elements and Original Attributes
    LIST_ATTR = _list{}
    LIST_FOUND -> AttributeCreator_10
AttributeCreator_10
    ATTR_LIST = Valeur,@Value(_list),identifiant,1
    -> DateFormatter_2
DateFormatter_2
    DATE_ATTR = Date
    FMT = ISO Date (%Y-%m-%d)
    SRCFMT = Unknown - Automatic Detection
    INVALID_DATE_VALUE = _FME_NO_OP_
    -> Tester_13
Tester_13
    TEST_MODE = Automatic
    TEST_DESCRIPTION = ""
    BOOL_OP = OR
    TEST_CLAUSE = TEST @Value(Keywords) = Keywordfree
    FAILED -> BulkAttributeRenamer_2
    PASSED -> DuplicateRemover_2
    PASSED -> BulkAttributeRenamer_3
BulkAttributeRenamer_2
    REPLACE_STR = Keywords_
    ATTRCHOICE = All Attributes
    PATTERN_ACTION_DISP = Add String Prefix
    -> AttributeFilter
AttributeFilter
    ATTR_NAME = Keywords_Nom
    ATTR_VALUES = <EMPTY>,<MISSING>,<NULL>,<UNFILTERED>,GEMET - INSPIRE themes, version 1.0,Thèmes du géoportail wallon, version 1.0,GEMET - Concepts, version 2.4,GEMET - Themes, version 2.4,Mots-clés InfraSIG
    GEMET - INSPIRE themes, version 1.0 -> DuplicateRemover_3
    Thèmes du géoportail wallon, version 1.0 -> DuplicateRemover_4
    GEMET - Concepts, version 2.4 -> DuplicateRemover_5
    GEMET - Themes, version 2.4 -> DuplicateRemover_6
    Mots-clés InfraSIG -> DuplicateRemover_7
    GEMET - INSPIRE themes, version 1.0 -> XMLTemplater_3 [input 4]
    Thèmes du géoportail wallon, version 1.0 -> XMLTemplater_3 [input 5]
    GEMET - Concepts, version 2.4 -> XMLTemplater_3 [input 6]
    GEMET - Themes, version 2.4 -> XMLTemplater_3 [input 7]
    Mots-clés InfraSIG -> DuplicateRemover_8
DuplicateRemover_3
    KEYATTR = Keywords_Nom
    UNIQUE -> XMLTemplater_3 [input 9]
DuplicateRemover_4
    KEYATTR = Keywords_Nom
    UNIQUE -> XMLTemplater_3 [input 10]
DuplicateRemover_5
    KEYATTR = Keywords_Nom
    UNIQUE -> XMLTemplater_3 [input 11]
DuplicateRemover_8
    KEYATTR = Keywords_Valeur
    UNIQUE -> XMLTemplater_3 [input 8]
DuplicateRemover_6
    KEYATTR = Keywords_Nom
    UNIQUE -> XMLTemplater_3 [input 12]
DuplicateRemover_7
    KEYATTR = Keywords_Nom
    UNIQUE -> XMLTemplater_3 [input 13]
XMLTemplater_3
    KEYWORDS_INFO_INFRASIG_QUERY_EXPR:
          <gmd:descriptiveKeywords>
      				<gmd:MD_Keywords>
      					{fme:process-features("KEYWORDS_VALUE_INFRASIG")}
      					<gmd:type>
      						<gmd:MD_KeywordTypeCode codeList="http://standards.iso.org/ittf/PubliclyAvailableStandards/ISO_19139_Schemas/resources/Codelist/ML_gmxCodelists.xml#MD_KeywordTypeCode" codeListValue="theme"/>
      					</gmd:type>
      					<gmd:thesaurusName>
      						<gmd:CI_Citation>
      							<gmd:title>
      								<gco:CharacterString>{fme:get-attribute("Keywords_Nom")}</gco:CharacterString>
      							</gmd:title>
      							<gmd:date>
      								<gmd:CI_Date>
      									<gmd:date>
      										<gco:Date>{fme:get-attribute("Keywords_Date")}</gco:Date>
      									</gmd:date>
      									<gmd:dateType>
      										<gmd:CI_DateTypeCode codeList="http://standards.iso.org/ittf/PubliclyAvailableStandards/ISO_19139_Schemas/resources/Codelist/ML_gmxCodelists.xml#CI_DateTypeCode" codeListValue="{fme:get-attribute("Keywords_Type de date")}"/>
      									</gmd:dateType>
      								</gmd:CI_Date>
      							</gmd:date>
      						</gmd:CI_Citation>
      					</gmd:thesaurusName>
      				</gmd:MD_Keywords>
      			</gmd:descriptiveKeywords>
    KEYWORDS_VALUE_GEOPORTAIL_QUERY_EXPR:
      <gmd:keyword>
      <gco:CharacterString>{fme:get-attribute("Keywords_Valeur")}</gco:CharacterString>
      </gmd:keyword>
    ROOT_QUERY_EXPR:
      <?xml version="1.0" encoding="UTF-8"?>
      <rw:MD_Metadata xmlns:rw="http://metawal.wallonie.be/schemas/3.0" xmlns:gmd="http://www.isotc211.org/2005/gmd" xmlns:gts="http://www.isotc211.org/2005/gts" xmlns:gco="http://www.isotc211.org/2005/gco" xmlns:gml="http://www.opengis.net/gml" xmlns:geonet="http://www.fao.org/geonetwork" xmlns:xsi="http://www.w3.org/2001/XMLSchema-instance" gco:isoType="gmd:MD_Metadata" xsi:schemaLocation="http://metawal.wallonie.be/schemas/3.0 file:///H:/gimb14/c/c130606/data/schemas/rwschema.xsd">
      {fme:process-features("KEYWORD_INFO_FREE")}
      {fme:process-features("KEYWORDS_INFO_INSPIRE")}
      {fme:process-features("KEYWORDS_INFO_G_CONCEPT")}
      {fme:process-features("KEYWORDS_INFO_G_THEMES")}
      {fme:process-features("KEYWORDS_INFO_GEOPORTAIL")}
      {fme:process-features("KEYWORDS_INFO_INFRASIG")}
      </rw:MD_Metadata>
    KEYWORDS_VALUE_G_CONCEPT_QUERY_EXPR:
      <gmd:keyword>
      <gco:CharacterString>{fme:get-attribute("Keywords_Valeur")}</gco:CharacterString>
      </gmd:keyword>
    KEYWORDS_INFO_G_THEMES_QUERY_EXPR:
          <gmd:descriptiveKeywords>
      				<gmd:MD_Keywords>
      					{fme:process-features("KEYWORDS_VALUE_G_THEMES")}
      					<gmd:type>
      						<gmd:MD_KeywordTypeCode codeList="http://standards.iso.org/ittf/PubliclyAvailableStandards/ISO_19139_Schemas/resources/Codelist/ML_gmxCodelists.xml#MD_KeywordTypeCode" codeListValue="theme"/>
      					</gmd:type>
      					<gmd:thesaurusName>
      						<gmd:CI_Citation>
      							<gmd:title>
      								<gco:CharacterString>{fme:get-attribute("Keywords_Nom")}</gco:CharacterString>
      							</gmd:title>
      							<gmd:date>
      								<gmd:CI_Date>
      									<gmd:date>
      										<gco:Date>{fme:get-attribute("Keywords_Date")}</gco:Date>
      									</gmd:date>
      									<gmd:dateType>
      										<gmd:CI_DateTypeCode codeList="http://standards.iso.org/ittf/PubliclyAvailableStandards/ISO_19139_Schemas/resources/Codelist/ML_gmxCodelists.xml#CI_DateTypeCode" codeListValue="{fme:get-attribute("Keywords_Type de date")}"/>
      									</gmd:dateType>
      								</gmd:CI_Date>
      							</gmd:date>
      						</gmd:CI_Citation>
      					</gmd:thesaurusName>
      				</gmd:MD_Keywords>
      			</gmd:descriptiveKeywords>
    VISIBLE_QUERY_VALIDATE = Yes
    KEYWORDS_VALUE_INFRASIG_QUERY_EXPR:
      <gmd:keyword>
      <gco:CharacterString>{fme:get-attribute("Keywords_Valeur")}</gco:CharacterString>
      </gmd:keyword>
    KEYWORDS_INFO_GEOPORTAIL_QUERY_EXPR:
          <gmd:descriptiveKeywords>
      				<gmd:MD_Keywords>
      					{fme:process-features("KEYWORDS_VALUE_GEOPORTAIL")}
      					<gmd:type>
      						<gmd:MD_KeywordTypeCode codeList="http://standards.iso.org/ittf/PubliclyAvailableStandards/ISO_19139_Schemas/resources/Codelist/ML_gmxCodelists.xml#MD_KeywordTypeCode" codeListValue="theme"/>
      					</gmd:type>
      					<gmd:thesaurusName>
      						<gmd:CI_Citation>
      							<gmd:title>
      								<gco:CharacterString>{fme:get-attribute("Keywords_Nom")}</gco:CharacterString>
      							</gmd:title>
      							<gmd:date>
      								<gmd:CI_Date>
      									<gmd:date>
      										<gco:Date>{fme:get-attribute("Keywords_Date")}</gco:Date>
      									</gmd:date>
      									<gmd:dateType>
      										<gmd:CI_DateTypeCode codeList="http://standards.iso.org/ittf/PubliclyAvailableStandards/ISO_19139_Schemas/resources/Codelist/ML_gmxCodelists.xml#CI_DateTypeCode" codeListValue="{fme:get-attribute("Keywords_Type de date")}"/>
      									</gmd:dateType>
      								</gmd:CI_Date>
      							</gmd:date>
      						</gmd:CI_Citation>
      					</gmd:thesaurusName>
      				</gmd:MD_Keywords>
      			</gmd:descriptiveKeywords>
    KEYWORDS_VALUE_INSPIRE_QUERY_EXPR:
      <gmd:keyword>
          <gco:CharacterString>{fme:get-attribute("Keywords_Valeur")}</gco:CharacterString>
      </gmd:keyword>
    OUTPUT_XML_HEADER = Yes
    KEYWORDS_INFO_G_CONCEPT_QUERY_EXPR:
          <gmd:descriptiveKeywords>
      				<gmd:MD_Keywords>
      					{fme:process-features("KEYWORDS_VALUE_G_CONCEPT")}
      					<gmd:type>
      						<gmd:MD_KeywordTypeCode codeList="http://standards.iso.org/ittf/PubliclyAvailableStandards/ISO_19139_Schemas/resources/Codelist/ML_gmxCodelists.xml#MD_KeywordTypeCode" codeListValue="theme"/>
      					</gmd:type>
      					<gmd:thesaurusName>
      						<gmd:CI_Citation>
      							<gmd:title>
      								<gco:CharacterString>{fme:get-attribute("Keywords_Nom")}</gco:CharacterString>
      							</gmd:title>
      							<gmd:date>
      								<gmd:CI_Date>
      									<gmd:date>
      										<gco:Date>{fme:get-attribute("Keywords_Date")}</gco:Date>
      									</gmd:date>
      									<gmd:dateType>
      										<gmd:CI_DateTypeCode codeList="http://standards.iso.org/ittf/PubliclyAvailableStandards/ISO_19139_Schemas/resources/Codelist/ML_gmxCodelists.xml#CI_DateTypeCode" codeListValue="{fme:get-attribute("Keywords_Type de date")}"/>
      									</gmd:dateType>
      								</gmd:CI_Date>
      							</gmd:date>
      						</gmd:CI_Citation>
      					</gmd:thesaurusName>
      				</gmd:MD_Keywords>
      			</gmd:descriptiveKeywords>
    KEYWORDS_VALUE_G_THEMES_QUERY_EXPR:
      <gmd:keyword>
      <gco:CharacterString>{fme:get-attribute("Keywords_Valeur")}</gco:CharacterString>
      </gmd:keyword>
    KEYWORDS_INFO_INSPIRE_QUERY_EXPR:
          <gmd:descriptiveKeywords>
      				<gmd:MD_Keywords>
      					{fme:process-features("KEYWORDS_VALUE_INSPIRE")}
      					<gmd:type>
      						<gmd:MD_KeywordTypeCode codeList="http://standards.iso.org/ittf/PubliclyAvailableStandards/ISO_19139_Schemas/resources/Codelist/ML_gmxCodelists.xml#MD_KeywordTypeCode" codeListValue="theme"/>
      					</gmd:type>
      					<gmd:thesaurusName>
      						<gmd:CI_Citation>
      							<gmd:title>
      								<gco:CharacterString>{fme:get-attribute("Keywords_Nom")}</gco:CharacterString>
      							</gmd:title>
      							<gmd:date>
      								<gmd:CI_Date>
      									<gmd:date>
      										<gco:Date>{fme:get-attribute("Keywords_Date")}</gco:Date>
      									</gmd:date>
      									<gmd:dateType>
      										<gmd:CI_DateTypeCode codeList="http://standards.iso.org/ittf/PubliclyAvailableStandards/ISO_19139_Schemas/resources/Codelist/ML_gmxCodelists.xml#CI_DateTypeCode" codeListValue="{fme:get-attribute("Keywords_Type de date")}"/>
      									</gmd:dateType>
      								</gmd:CI_Date>
      							</gmd:date>
      						</gmd:CI_Citation>
      					</gmd:thesaurusName>
      				</gmd:MD_Keywords>
      			</gmd:descriptiveKeywords>
    KEYWORD_INFO_FREE_QUERY_EXPR:
      		<gmd:descriptiveKeywords>
      				<gmd:MD_Keywords>
      {fme:process-features("KEYWORD_FREE_VALUE")}
      				</gmd:MD_Keywords>
      			</gmd:descriptiveKeywords>
    RESULT_ATTRIBUTE = _result
    KEYWORD_FREE_VALUE_QUERY_EXPR = <gmd:keyword><gco:CharacterString>{fme:get-attribute("Keywordsfree_Valeur")}</gco:CharacterString></gmd:keyword>
    -> modif_texte
modif_texte
    _RESULT = @Value(_result)
    StringReplacer_2_Output -> XMLTemplater_2 [input 15]

Bookmark: Scope INSPIRE
synthese/ScopeINSPIRE (reader XLSXR_1)
    attributes: Nom char(14), Valeur char(3)
    -> AttributeCreator_11
AttributeCreator_11
    ATTR_LIST = join,1
    -> FeatureMerger_5 [input 1]
FeatureMerger_5
    PROCESS_DUPS = No
    MERGE_TYPE = Attributes Only
    SUPPLIERS_FIRST = No
    JOIN_KEYS = @Value(join) @Value(join) AUTO
    SUPPLIER_PREFIX_DUMMY = YES
    MERGED -> FeatureMerger_2 [input 2]

Bookmark: FREE
DuplicateRemover_2
    KEYATTR = identifiant
    UNIQUE -> XMLTemplater_3 [input 2]
BulkAttributeRenamer_3
    REPLACE_STR = Keywordsfree_
    ATTRCHOICE = All Attributes
    PATTERN_ACTION_DISP = Add String Prefix
    -> XMLTemplater_3 [input 3]

Bookmark: ISO
synthese/ISO_Topic (reader XLSXR_1)
    attributes: Nom char(17), Valeur number(2,0)
    -> Tester_5
Tester_5
    TEST_MODE = Automatic
    TEST_DESCRIPTION = ""
    BOOL_OP = OR
    TEST_CLAUSE:
      TEST @Value(Valeur) = Valeur
      TEST Valeur ATTRIBUTE_IS_MISSING ""
    FAILED -> AttributeSplitter
AttributeSplitter
    LIST_NAME = _list
    ATTR_NAME = Valeur
    DELIMITER = ;
    TRIM_OPTION = Both
    DROP_EMPTY_PARTS = No
    -> ListExploder
ListExploder
    INDEX_ATTR = _element_index
    MODE = List Elements and Original Attributes
    LIST_ATTR = _list{}
    LIST_FOUND -> AttributeCreator
AttributeCreator
    ATTR_LIST = Valeur,@Value(_list)
    -> AttributeValueMapper_2
AttributeValueMapper_2
    DIRECTION = Forward (Source To Destination)
    VAL_ATTR = Valeur
    LUT = Biologie, faune et flore,biota,Cadastre, aménagement,planningCadastre,Carte de référence de la couverture terrestre,imageryBaseMapsEarthCover,Climatologie, météorologie,climatologyMeteorologyAtmospher,Constructions et ouvrages,structure,Eaux intérieures, hydrographie,inlandWaters,Infrastructures de transport,transportation,Infrastructures militaires,intelligenceMilitary,Limites politiques et administratives,boundaries,Sciences de la terre, géosciences,geoscientificInformation,Télécommunication, approvisionnement et énergie,utilitiesCommunication,Agriculture,farming,Altimétrie,elevation,Economie,economy,Environnement,environment,Localisation,location,Océans,oceans,Santé,health,Société,society
    SRC = Valeur
    -> BulkAttributeRenamer_4
BulkAttributeRenamer_4
    REPLACE_STR = ISO_
    ATTRCHOICE = All Attributes
    PATTERN_ACTION_DISP = Add String Prefix
    -> XMLTemplater_2 [input 24]

Bookmark: Denominator Distance
synthese/denominator (reader XLSXR_1)
    attributes: Nom char(12), Valeur string
    -> Tester_6
Tester_6
    TEST_MODE = Automatic
    TEST_DESCRIPTION = ""
    BOOL_OP = OR
    TEST_CLAUSE:
      TEST @Value(Valeur) = Valeur
      TEST Valeur ATTRIBUTE_IS_EMPTY ""
    FAILED -> BulkAttributeRenamer_5
BulkAttributeRenamer_5
    REPLACE_STR = Denominator_
    ATTRCHOICE = All Attributes
    PATTERN_ACTION_DISP = Add String Prefix
    -> XMLTemplater_2 [input 22]
synthese/Distance (reader XLSXR_1)
    attributes: Nom char(9), Valeur string
    -> Tester_7
Tester_7
    TEST_MODE = Automatic
    TEST_DESCRIPTION = ""
    BOOL_OP = OR
    TEST_CLAUSE:
      TEST @Value(Valeur) = Valeur
      TEST Valeur ATTRIBUTE_IS_EMPTY ""
    FAILED -> BulkAttributeRenamer_6
BulkAttributeRenamer_6
    REPLACE_STR = Distance_
    ATTRCHOICE = All Attributes
    PATTERN_ACTION_DISP = Add String Prefix
    -> XMLTemplater_2 [input 23]
Distributor
    CONTACTSUPP_COUNTRY = @Value(Contactsupp_country)
    CONTACTSUPP_INDIVIDUALNAME = @Value(Contactsupp_individualName)
    DISTRIBUTIONONLINE_DISTRIBUTEUR = @Value(Contactsupp_Distributeur)
    CONTACTSUPP_ROLE = @Value(Contactsupp_Role)
    CONTACTSUPP_ORGANISATIONNAME = @Value(Contactsupp_organisationName)
    CONTACTSUPP_DESCRIPTION = @Value(Contactsupp_description)
    CONTACTSUPP__COUNT = @Value(Contactsupp__count)
    CONTACTSUPP_FUNCTION = @Value(Contactsupp_function)
    CONTACTSUPP_ELECTRONICMAILADDRESS = @Value(Contactsupp_electronicMailAddress)
    CONTACTSUPP_VOICE = @Value(Contactsupp_voice)
    CONTACTSUPP_CITY = @Value(Contactsupp_city)
    CONTACTSUPP_LINKAGE = @Value(Contactsupp_linkage)
    CONTACTSUPP_DELIVERYPOINT = @Value(Contactsupp_deliveryPoint)
    CONTACTSUPP_NAME = @Value(Contactsupp_name)
    CONTACTSUPP_POSTALCODE = @Value(Contactsupp_postalCode)
    CONTACTSUPP__ELEMENT_INDEX = @Value(Contactsupp__element_index)
    CONTACTSUPP_POSITIONNAME = @Value(Contactsupp_positionName)
    CONTACTSUPP_ROLE_TYPE = @Value(Contactsupp_Role_type)
    CONTACTSUPP_PROTOCOLE = @Value(Contactsupp_protocole)
    modif_texte_8_StringReplacer_2_Output_2 -> modif_texte_10
modif_texte_10
    _RESULT = @Value(_result)
    StringReplacer_2_Output -> AttributeKeeper_4
AttributeKeeper_4
    KEEP_ATTRS = Contactsupp__count,_result
    -> AttributeRenamer_4
AttributeRenamer_4
    ATTR_LIST = Contactsupp__count,count,""
    -> DuplicateRemover_19
    -> XMLTemplater [input 4]

Bookmark: Distribution
synthese/online_full (reader XLSXR_1)
    attributes: Distributeur string, orderingInstructions1 string, nameformat1 string, versionFormat1 string, transfersize1 (créer bloc xml) string, dirstributionURLdl string, distributionProtocoldl char(13), distributionNamedl string, distributionDescriptiodl char(32), distributionFunctiodl char(9), Element_ISO string
    -> AttributeValueMapper_5
synthese/full_online2 (reader XLSXR_1)
    attributes: Distributeur string, orderingInstructions1 string, nameformat1 string, versionFormat1 string, transfersize1 (créer bloc xml) string, dirstributionURLdl string, distributionProtocoldl string, distributionNamedl string, distributionDescriptiodl char(32), distributionFunctiodl char(9), Element_ISO string
    -> AttributeValueMapper_5
AttributeValueMapper_5
    DIRECTION = Forward (Source To Destination)
    VAL_ATTR = distributionProtocoldl
    LUT = Adresse Internet (URL),WWW:LINK-1.0-http--link,Base de données ORACLE,DB:ORACLE,Base de données PostGIS,DB:POSTGIS,Data Turbine,RBNB:DATATURBINE,ESRI-REST GeoService,ESRI:REST,Ficher vecteur,FILE:GEO,Fichier raster,FILE:RASTER,Fichier tabulaire,FILE:TAB,Fichier à télécharger (FTP),WWW:DOWNLOAD-1.0-ftp--download,Fichier à télécharger (http),WWW:DOWNLOAD-1.0-http--download,Fil RSS (URL),WWW:LINK-1.0-http--rss,OGC-CSW Catalogue Service for the Web,OGC:CSW,OGC-GML Geography Markup Language,OGC:GML,OGC-KML Keyhole Markup Language,OGC:KML,OGC-ODS OpenLS Directory Service,OGC:ODS,OGC-ODS OpenLS Gateway Service,OGC:OGS,OGC-ODS OpenLS Presentation Service,OGC:OPS,OGC-ODS OpenLS Route Service,OGC:ORS,OGC-ODS OpenLS Utility Service,OGC:OUS,OGC-SAS Sensor Alert Service,OGC:SAS,OGC-SOS Sensor Observation Service,OGC:SOS,OGC-SPS Sensor Planning Service,OGC:SPS,OGC-WCS Web Coverage Service,OGC:WCS,OGC-WCTS Web Coordinate Transformation Service,OGC:WCTS,OGC-WFS Web Feature Service,OGC:WFS,OGC-WFS-G Gazzetteer Service,OGC:WFS-G,OGC-WMC Web Map Context,OGC:WMC,OGC-WMS Web Map Service,OGC:WMS,OGC-WNS Web Notification Service,OGC:WNS,OGC-WPS Web Processing Service,OGC:WPS,OPeNDAP URL,WWW:LINK-1.0-http--opendap,Unknown Service Type,UKST,iCalendar (URL),WWW:LINK-1.0-http--ical
    SRC = distributionProtocoldl
    -> FeatureMerger_3 [input 1]
FeatureMerger_3
    PROCESS_DUPS = No
    MERGE_TYPE = Attributes Only
    SUPPLIERS_FIRST = No
    JOIN_KEYS = @Value(Distributeur) @Value(organisationName) AUTO
    SUPPLIER_PREFIX_DUMMY = YES
    MERGED -> Counter_4
Counter_4
    SCOPE = Global
    START = 0
    DOMAIN = counter
    CNT_ATTR = _count
    -> BulkAttributeRenamer_7
    -> BulkAttributeRenamer_21
BulkAttributeRenamer_21
    REPLACE_STR = Contactsupp_
    ATTRCHOICE = All Attributes
    PATTERN_ACTION_DISP = Add String Prefix
    -> Distributor
BulkAttributeRenamer_7
    REPLACE_STR = Distributiononline_
    ATTRCHOICE = All Attributes
    PATTERN_ACTION_DISP = Add String Prefix
    -> distri_online
distri_online
    DISTRIBUTIONONLINE_ELECTRONICMAILADDRESS = @Value(Distributiononline_electronicMailAddress)
    DISTRIBUTIONONLINE_POSTALCODE = @Value(Distributiononline_postalCode)
    DISTRIBUTIONONLINE_DESCRIPTION = @Value(Distributiononline_description)
    DISTRIBUTIONONLINE_DISTRIBUTEUR = @Value(Distributiononline_Distributeur)
    DISTRIBUTIONONLINE_VERSIONFORMAT1 = @Value(Distributiononline_versionFormat1)
    DISTRIBUTIONONLINE_NAMEFORMAT1 = @Value(Distributiononline_nameformat1)
    DISTRIBUTIONONLINE_FUNCTION = @Value(Distributiononline_function)
    DISTRIBUTIONONLINE_DISTRIBUTIONNAMEDL = @Value(Distributiononline_distributionNamedl)
    DISTRIBUTIONONLINE_DELIVERYPOINT = @Value(Distributiononline_deliveryPoint)
    DISTRIBUTIONONLINE_DISTRIBUTIONDESCRIPTIODL = @Value(Distributiononline_distributionDescriptiodl)
    DISTRIBUTIONONLINE_DISTRIBUTIONPROTOCOLDL = @Value(Distributiononline_distributionProtocoldl)
    DISTRIBUTIONONLINE_ORGANISATIONNAME = @Value(Distributiononline_organisationName)
    DISTRIBUTIONONLINE_VOICE = @Value(Distributiononline_voice)
    DISTRIBUTIONONLINE_LINKAGE = @Value(Distributiononline_linkage)
    DISTRIBUTIONONLINE_ROLE_TYPE = @Value(Distributiononline_Role_type)
    DISTRIBUTIONONLINE_TRANSFERSIZE1__CRÉER_BLOC_XML_ = @Value(Distributiononline_transfersize1 (créer bloc xml))
    DISTRIBUTIONONLINE_ELEMENT_ISO = @Value(Distributiononline_Element_ISO)
    DISTRIBUTIONONLINE_PROTOCOLE = @Value(Distributiononline_protocole)
    DISTRIBUTIONONLINE_ROLE = @Value(Distributiononline_Role)
    DISTRIBUTIONONLINE_ORDERINGINSTRUCTIONS1 = @Value(Distributiononline_orderingInstructions1)
    DISTRIBUTIONONLINE__COUNT = @Value(Distributiononline__count)
    DISTRIBUTIONONLINE_CITY = @Value(Distributiononline_city)
    DISTRIBUTIONONLINE_DIRSTRIBUTIONURLDL = @Value(Distributiononline_dirstributionURLdl)
    DISTRIBUTIONONLINE_DISTRIBUTIONFUNCTIODL = @Value(Distributiononline_distributionFunctiodl)
    DISTRIBUTIONONLINE__ELEMENT_INDEX = @Value(Distributiononline__element_index)
    DISTRIBUTIONONLINE_NAME = @Value(Distributiononline_name)
    DISTRIBUTIONONLINE_POSITIONNAME = @Value(Distributiononline_positionName)
    DISTRIBUTIONONLINE_COUNTRY = @Value(Distributiononline_country)
    DISTRIBUTIONONLINE_INDIVIDUALNAME = @Value(Distributiononline_individualName)
    Tester_39_Passed -> modif_texte_13
modif_texte_13
    _RESULT = @Value(_result)
    StringReplacer_2_Output -> AttributeKeeper_5
AttributeKeeper_5
    KEEP_ATTRS = Distributiononline__count,_result
    -> AttributeRenamer_6
AttributeRenamer_6
    ATTR_LIST = Distributiononline__count,count,""
    -> DuplicateRemover_19
    -> XMLTemplater [input 3]
synthese/acces_limite (reader XLSXR_1)
    attributes: dirstributionURLApp char(7), distributionProtocolApp string, distributionNameApp string, distributionDescriptioApp string, distributionFunctioApp string, Element_ISO string
    -> AttributeValueMapper_6
AttributeValueMapper_6
    DIRECTION = Forward (Source To Destination)
    VAL_ATTR = distributionProtocolApp
    LUT = Adresse Internet (URL),WWW:LINK-1.0-http--link,Base de données ORACLE,DB:ORACLE,Base de données PostGIS,DB:POSTGIS,Data Turbine,RBNB:DATATURBINE,ESRI-REST GeoService,ESRI:REST,Ficher vecteur,FILE:GEO,Fichier raster,FILE:RASTER,Fichier tabulaire,FILE:TAB,Fichier à télécharger (FTP),WWW:DOWNLOAD-1.0-ftp--download,Fichier à télécharger (http),WWW:DOWNLOAD-1.0-http--download,Fil RSS (URL),WWW:LINK-1.0-http--rss,OGC-CSW Catalogue Service for the Web,OGC:CSW,OGC-GML Geography Markup Language,OGC:GML,OGC-KML Keyhole Markup Language,OGC:KML,OGC-ODS OpenLS Directory Service,OGC:ODS,OGC-ODS OpenLS Gateway Service,OGC:OGS,OGC-ODS OpenLS Presentation Service,OGC:OPS,OGC-ODS OpenLS Route Service,OGC:ORS,OGC-ODS OpenLS Utility Service,OGC:OUS,OGC-SAS Sensor Alert Service,OGC:SAS,OGC-SOS Sensor Observation Service,OGC:SOS,OGC-SPS Sensor Planning Service,OGC:SPS,OGC-WCS Web Coverage Service,OGC:WCS,OGC-WCTS Web Coordinate Transformation Service,OGC:WCTS,OGC-WFS Web Feature Service,OGC:WFS,OGC-WFS-G Gazzetteer Service,OGC:WFS-G,OGC-WMC Web Map Context,OGC:WMC,OGC-WMS Web Map Service,OGC:WMS,OGC-WNS Web Notification Service,OGC:WNS,OGC-WPS Web Processing Service,OGC:WPS,OPeNDAP URL,WWW:LINK-1.0-http--opendap,Unknown Service Type,UKST,iCalendar (URL),WWW:LINK-1.0-http--ical
    SRC = distributionProtocolApp
    -> BulkAttributeRenamer_12
synthese/site_rapport (reader XLSXR_1)
    attributes: dirstributionURLsit string, distributionProtocolsit string, distributionNamesit string, distributionDescriptiosit string, distributionFunctiosit string
    -> Tester_42
Tester_42
    TEST_MODE = Automatic
    TEST_DESCRIPTION = ""
    BOOL_OP = AND
    TEST_CLAUSE:
      TEST dirstributionURLsit NOT_ATTRIBUTE_VALUE_NULL ""
      TEST dirstributionURLsit NOT_ATTRIBUTE_IS_EMPTY ""
      TEST dirstributionURLsit NOT_ATTRIBUTE_IS_MISSING ""
    PASSED -> AttributeRenamer_3
AttributeRenamer_3
    ATTR_LIST = dirstributionURLsit,dirstributionURLApp,"",distributionDescriptiosit,distributionDescriptioApp,"",distributionFunctiosit,distributionFunctioApp,"",distributionNamesit,distributionNameApp,"",distributionProtocolsit,distributionProtocolApp,""
    -> BulkAttributeRenamer_12
BulkAttributeRenamer_12
    REPLACE_STR = Distributionacceslimite_
    ATTRCHOICE = All Attributes
    PATTERN_ACTION_DISP = Add String Prefix
    -> Counter_5
Counter_5
    SCOPE = Global
    START = 0
    DOMAIN = counter
    CNT_ATTR = _count
    -> DISTRIBUTIONACCESLIMITEDOC
DISTRIBUTIONACCESLIMITEDOC
    DISTRIBUTIONACCESLIMITE_DISTRIBUTIONPROTOCOLAPP = @Value(Distributionacceslimite_distributionProtocolApp)
    DISTRIBUTIONACCESLIMITE_DISTRIBUTIONNAMEAPP = @Value(Distributionacceslimite_distributionNameApp)
    DISTRIBUTIONACCESLIMITE_DISTRIBUTIONFUNCTIOAPP = @Value(Distributionacceslimite_distributionFunctioApp)
    _COUNT = @Value(_count)
    DISTRIBUTIONACCESLIMITE_ELEMENT_ISO = @Value(Distributionacceslimite_Element_ISO)
    DISTRIBUTIONACCESLIMITE_DISTRIBUTIONDESCRIPTIOAPP = @Value(Distributionacceslimite_distributionDescriptioApp)
    DISTRIBUTIONACCESLIMITE_DIRSTRIBUTIONURLAPP = @Value(Distributionacceslimite_dirstributionURLApp)
    -> modif_texte_16
modif_texte_16
    _RESULT = @Value(_result)
    StringReplacer_2_Output -> XMLTemplater_2 [input 19]
synthese/offline (reader XLSXR_1)
    attributes: Distributeur string, orderingInstructions3 string, nameformat3 char(17), versionFormat3 string, transfersize3 (créer bloc xml) string, mediumName string, mediumNameCode string
    -> FeatureMerger_4 [input 1]
synthese/Offline_2 (reader XLSXR_1)
    attributes: Distributeur string, orderingInstructions3 string, nameformat3 string, versionFormat3 string, transfersize3 (créer bloc xml) string, mediumName string, mediumNameCode string
    -> FeatureMerger_4 [input 1]
FeatureMerger_4
    PROCESS_DUPS = No
    MERGE_TYPE = Attributes Only
    SUPPLIERS_FIRST = No
    JOIN_KEYS = @Value(Distributeur) @Value(organisationName) AUTO
    SUPPLIER_PREFIX_DUMMY = YES
    MERGED -> Counter_3
Counter_3
    SCOPE = Global
    START = 0
    DOMAIN = counter
    CNT_ATTR = _count
    -> BulkAttributeRenamer_22
    -> BulkAttributeRenamer_13
BulkAttributeRenamer_22
    REPLACE_STR = Contactsupp_
    ATTRCHOICE = All Attributes
    PATTERN_ACTION_DISP = Add String Prefix
    -> Distributor_2
Distributor_2
    CONTACTSUPP_COUNTRY = @Value(Contactsupp_country)
    CONTACTSUPP_INDIVIDUALNAME = @Value(Contactsupp_individualName)
    DISTRIBUTIONONLINE_DISTRIBUTEUR = @Value(Contactsupp_Distributeur)
    CONTACTSUPP_ROLE = @Value(Contactsupp_Role)
    CONTACTSUPP_ORGANISATIONNAME = @Value(Contactsupp_organisationName)
    CONTACTSUPP_DESCRIPTION = @Value(Contactsupp_description)
    CONTACTSUPP__COUNT = @Value(Contactsupp__count)
    CONTACTSUPP_FUNCTION = @Value(Contactsupp_function)
    CONTACTSUPP_ELECTRONICMAILADDRESS = @Value(Contactsupp_electronicMailAddress)
    CONTACTSUPP_VOICE = @Value(Contactsupp_voice)
    CONTACTSUPP_CITY = @Value(Contactsupp_city)
    CONTACTSUPP_LINKAGE = @Value(Contactsupp_linkage)
    CONTACTSUPP_DELIVERYPOINT = @Value(Contactsupp_deliveryPoint)
    CONTACTSUPP_NAME = @Value(Contactsupp_name)
    CONTACTSUPP_POSTALCODE = @Value(Contactsupp_postalCode)
    CONTACTSUPP__ELEMENT_INDEX = @Value(Contactsupp__element_index)
    CONTACTSUPP_POSITIONNAME = @Value(Contactsupp_positionName)
    CONTACTSUPP_ROLE_TYPE = @Value(Contactsupp_Role_type)
    CONTACTSUPP_PROTOCOLE = @Value(Contactsupp_protocole)
    modif_texte_8_StringReplacer_2_Output_2 -> modif_texte_2
modif_texte_2
    _RESULT = @Value(_result)
    StringReplacer_2_Output -> AttributeKeeper_6
AttributeKeeper_6
    KEEP_ATTRS = Contactsupp__count,_result
    -> AttributeRenamer_8
AttributeRenamer_8
    ATTR_LIST = Contactsupp__count,count,""
    -> DuplicateRemover_14
    -> XMLTemplater_11 [input 4]
BulkAttributeRenamer_13
    REPLACE_STR = Distributiononline_
    ATTRCHOICE = All Attributes
    PATTERN_ACTION_DISP = Add String Prefix
    -> distri_offline
distri_offline
    DISTRIBUTIONONLINE_ELECTRONICMAILADDRESS = @Value(Distributiononline_electronicMailAddress)
    DISTRIBUTIONONLINE_POSTALCODE = @Value(Distributiononline_postalCode)
    DISTRIBUTIONONLINE_DESCRIPTION = @Value(Distributiononline_description)
    DISTRIBUTIONONLINE_DISTRIBUTEUR = @Value(Distributiononline_Distributeur)
    DISTRIBUTIONONLINE_VERSIONFORMAT1 = @Value(Distributiononline_versionFormat3)
    DISTRIBUTIONONLINE_ORDERINGINSTRUCTIONS3 = @Value(Distributiononline_orderingInstructions3)
    DISTRIBUTIONONLINE_NAMEFORMAT1 = @Value(Distributiononline_nameformat3)
    DISTRIBUTIONONLINE_FUNCTION = @Value(Distributiononline_function)
    DISTRIBUTIONONLINE_DISTRIBUTIONNAMEDL = @Value(Distributiononline_name)
    DISTRIBUTIONONLINE_DELIVERYPOINT = @Value(Distributiononline_deliveryPoint)
    DISTRIBUTIONONLINE_TRANSFERSIZE3__CRÉER_BLOC_XML_ = @Value(Distributiononline_transfersize3 (créer bloc xml))
    DISTRIBUTIONONLINE_DISTRIBUTEUR_2 = @Value(Distributiononline_Distributeur)
    DISTRIBUTIONONLINE_DISTRIBUTIONDESCRIPTIODL = @Value(Distributiononline_name)
    DISTRIBUTIONONLINE_DISTRIBUTIONPROTOCOLDL = @Value(Distributiononline_name)
    DISTRIBUTIONONLINE_ORGANISATIONNAME = @Value(Distributiononline_organisationName)
    DISTRIBUTIONONLINE_VERSIONFORMAT3 = @Value(Distributiononline_versionFormat3)
    DISTRIBUTIONONLINE__COUNT_2 = @Value(Distributiononline__count)
    DISTRIBUTIONONLINE_VOICE = @Value(Distributiononline_voice)
    DISTRIBUTIONONLINE_LINKAGE = @Value(Distributiononline_linkage)
    DISTRIBUTIONONLINE_ROLE_TYPE = @Value(Distributiononline_Role_type)
    DISTRIBUTIONONLINE_TRANSFERSIZE1__CRÉER_BLOC_XML_ = @Value(Distributiononline_transfersize3 (créer bloc xml))
    DISTRIBUTIONONLINE_ELEMENT_ISO = @Value(Distributiononline_name)
    DISTRIBUTIONONLINE_PROTOCOLE = @Value(Distributiononline_protocole)
    DISTRIBUTIONONLINE_ROLE = @Value(Distributiononline_Role)
    DISTRIBUTIONONLINE_MEDIUMNAMECODE = @Value(Distributiononline_mediumNameCode)
    DISTRIBUTIONONLINE_ORDERINGINSTRUCTIONS1 = @Value(Distributiononline_orderingInstructions3)
    DISTRIBUTIONONLINE__COUNT = @Value(Distributiononline__count)
    DISTRIBUTIONONLINE_MEDIUMNAMECODE_2 = @Value(Distributiononline_mediumNameCode)
    DISTRIBUTIONONLINE_CITY = @Value(Distributiononline_city)
    DISTRIBUTIONONLINE_DIRSTRIBUTIONURLDL = @Value(Distributiononline_name)
    DISTRIBUTIONONLINE_MEDIUMNAME = @Value(Distributiononline_mediumName)
    DISTRIBUTIONONLINE_DISTRIBUTIONFUNCTIODL = @Value(Distributiononline_name)
    DISTRIBUTIONONLINE__ELEMENT_INDEX = @Value(Distributiononline__element_index)
    DISTRIBUTIONONLINE_NAME = @Value(Distributiononline_name)
    DISTRIBUTIONONLINE_MEDIUMNAME_2 = @Value(Distributiononline_mediumName)
    DISTRIBUTIONONLINE_POSITIONNAME = @Value(Distributiononline_positionName)
    DISTRIBUTIONONLINE_COUNTRY = @Value(Distributiononline_country)
    DISTRIBUTIONONLINE_INDIVIDUALNAME = @Value(Distributiononline_individualName)
    DISTRIBUTIONONLINE_NAMEFORMAT3 = @Value(Distributiononline_nameformat3)
    Tester_39_Passed -> modif_texte_12
modif_texte_12
    _RESULT = @Value(_result)
    StringReplacer_2_Output -> AttributeKeeper_7
AttributeKeeper_7
    KEEP_ATTRS = Distributiononline__count,_result
    -> AttributeRenamer_7
AttributeRenamer_7
    ATTR_LIST = Distributiononline__count,count,""
    -> XMLTemplater_11 [input 3]
    -> DuplicateRemover_14

Bookmark: Distribution
DuplicateRemover_19
    KEYATTR = count
    UNIQUE -> XMLTemplater [input 2]
    UNIQUE -> XMLTemplater [input 1]
XMLTemplater
    GROUP_BY = count
    RESULT_ATTRIBUTE = _result
    ONLINE_QUERY_EXPR = {fme:get-attribute("_result")}
    CONSECUTIVE_GROUPS = No
    DISTRIBUTOR_INFO_QUERY_EXPR = {fme:get-attribute("_result")}
    ROOT_QUERY_EXPR:
      <?xml version="1.0" encoding="UTF-8"?>
      <rw:MD_Metadata xmlns:rw="http://metawal.wallonie.be/schemas/3.0" xmlns:gmd="http://www.isotc211.org/2005/gmd" xmlns:gts="http://www.isotc211.org/2005/gts" xmlns:gco="http://www.isotc211.org/2005/gco" xmlns:gml="http://www.opengis.net/gml" xmlns:geonet="http://www.fao.org/geonetwork" xmlns:xsi="http://www.w3.org/2001/XMLSchema-instance" gco:isoType="gmd:MD_Metadata" xsi:schemaLocation="http://metawal.wallonie.be/schemas/3.0 file:///H:/gimb14/c/c130606/data/schemas/rwschema.xsd">
      {fme:process-features("DISTRIBUTION_ONLINE")}
      </rw:MD_Metadata>
    VISIBLE_QUERY_VALIDATE = Yes
    DISTRIBUTION_ONLINE_QUERY_EXPR:
      <gmd:distributor>
      			<gmd:MD_Distributor>
      			{fme:process-features("DISTRIBUTOR_INFO")}
      			{fme:process-features("ONLINE")}
      			</gmd:MD_Distributor>
       </gmd:distributor>
    OUTPUT_XML_HEADER = Yes
    -> modif_texte_14
modif_texte_14
    _RESULT = @Value(_result)
    StringReplacer_2_Output -> StringReplacer_8

Bookmark: Hierarchy level
synthese/hierachy_level2 (reader XLSXR_1)
    attributes: Nom char(19), Valeur string
    -> Tester_9
Tester_9
    TEST_MODE = Automatic
    TEST_DESCRIPTION = ""
    BOOL_OP = OR
    TEST_CLAUSE:
      TEST @Value(Nom) = Nom
      TEST Valeur ATTRIBUTE_IS_EMPTY ""
    FAILED -> Tester_43
Tester_43
    TEST_MODE = Automatic
    TEST_DESCRIPTION = ""
    BOOL_OP = OR
    TEST_CLAUSE = TEST @Value(Valeur) = series
    PASSED -> BulkAttributeRenamer_8
BulkAttributeRenamer_8
    REPLACE_STR = hierarchylevel_
    ATTRCHOICE = All Attributes
    PATTERN_ACTION_DISP = Add String Prefix
    -> XMLTemplater_2 [input 16]

Bookmark: Conformance pass
synthese/conformance_pass (reader XLSXR_1)
    attributes: Nom char(16), Valeur char(12)
    -> Tester_4
Tester_4
    TEST_MODE = Automatic
    TEST_DESCRIPTION = ""
    BOOL_OP = OR
    TEST_CLAUSE = TEST @Value(Valeur) = Pas évaluée
    FAILED -> BulkAttributeRenamer_14
    PASSED -> XMLTemplater_8 [input 3]
    PASSED -> AttributeCreator_21
BulkAttributeRenamer_14
    REPLACE_STR = Conformance_pass
    ATTRCHOICE = All Attributes
    PATTERN_ACTION_DISP = Add String Prefix
    -> AttributeCreator_22

Bookmark: Conformance Pass
AttributeCreator_21
    ATTR_LIST = identifiant,45
    -> DuplicateRemover_15
AttributeCreator_22
    ATTR_LIST = identifiant,45
    -> DuplicateRemover_15
    -> XMLTemplater_8 [input 2]
DuplicateRemover_15
    KEYATTR = identifiant
    UNIQUE -> XMLTemplater_8 [input 1]
XMLTemplater_8
    RESULT_ATTRIBUTE = _result
    CONFORMANCEPASS_EVALUEE_QUERY_EXPR = <gmd:pass><gco:Boolean>{fme:get-attribute("Conformance_passValeur")}</gco:Boolean></gmd:pass>
    ROOT_QUERY_EXPR:
      <?xml version="1.0" encoding="UTF-8"?>
      <rw:MD_Metadata xmlns:rw="http://metawal.wallonie.be/schemas/3.0" xmlns:gmd="http://www.isotc211.org/2005/gmd" xmlns:gts="http://www.isotc211.org/2005/gts" xmlns:gco="http://www.isotc211.org/2005/gco" xmlns:gml="http://www.opengis.net/gml" xmlns:geonet="http://www.fao.org/geonetwork" xmlns:xsi="http://www.w3.org/2001/XMLSchema-instance" gco:isoType="gmd:MD_Metadata" xsi:schemaLocation="http://metawal.wallonie.be/schemas/3.0 file:///H:/gimb14/c/c130606/data/schemas/rwschema.xsd">
      {fme:process-features("CONFORMANCEPASS_EVALUEE")}
      {fme:process-features("CONFORMANCEPASS_PASEVALUEE")}
      </rw:MD_Metadata>
    CONFORMANCEPASS_PASEVALUEE_QUERY_EXPR = <gmd:pass gco:nilReason="unknown"> </gmd:pass>
    VISIBLE_QUERY_VALIDATE = Yes
    OUTPUT_XML_HEADER = Yes
    -> modif_texte_7
modif_texte_7
    _RESULT = @Value(_result)
    StringReplacer_2_Output -> XMLTemplater_2 [input 18]

Bookmark: Régime d'accés à la ressource (Acces Constraint and OtherConstraints)
synthese/regime_acces_ressource (reader XLSXR_1)
    attributes: Coché char(6), AccessConstraints char(20), Phrase char(111), Valeur string
    -> Tester_8
Tester_8
    TEST_MODE = Automatic
    TEST_DESCRIPTION = ""
    BOOL_OP = OR
    TEST_CLAUSE:
      TEST @Value(Coché) = Yes
      TEST @Value(Coché) = TRUE
    PASSED -> AttributeCreator_13
AttributeCreator_13
    ATTR_LIST = Valeur,@Value(Phrase) @Value(Valeur)
    -> BulkAttributeRenamer_15
    -> BulkAttributeRenamer_18
BulkAttributeRenamer_18
    REPLACE_STR = regime_acces_ressource
    ATTRCHOICE = All Attributes
    PATTERN_ACTION_DISP = Add String Prefix
    -> Tester_35
synthese/service_visusalisation (reader XLSXR_1)
    attributes: Coché char(3), Valeur char(67)
    -> Tester_20
Tester_20
    TEST_MODE = Automatic
    TEST_DESCRIPTION = ""
    BOOL_OP = OR
    TEST_CLAUSE = TEST @Value(Coché) = Yes
    PASSED -> BulkAttributeRenamer_17
BulkAttributeRenamer_17
    REPLACE_STR = regime_acces_ressource
    ATTRCHOICE = All Attributes
    PATTERN_ACTION_DISP = Add String Prefix
    -> Tester_32
BulkAttributeRenamer_15
    REPLACE_STR = regime_acces_ressource
    ATTRCHOICE = All Attributes
    PATTERN_ACTION_DISP = Add String Prefix
    -> AttributeCreator_17
    -> Tester_32
AttributeCreator_17
    ATTR_LIST = identifiant,33
    -> DuplicateRemover_9

Bookmark: Contraintes
Tester_35
    TEST_MODE = Automatic
    TEST_DESCRIPTION = ""
    BOOL_OP = OR
    TEST_CLAUSE = TEST 0 = 0
    PASSED -> XMLTemplater_7 [input 5]
    PASSED -> AttributeCreator_20
Tester_32
    TEST_MODE = Automatic
    TEST_DESCRIPTION = ""
    BOOL_OP = OR
    TEST_CLAUSE = TEST 0 = 0
    PASSED -> XMLTemplater_7 [input 4]
    PASSED -> AttributeCreator_20
Tester_34
    TEST_MODE = Automatic
    TEST_DESCRIPTION = ""
    BOOL_OP = OR
    TEST_CLAUSE = TEST 0 = 0
    PASSED -> AttributeCreator_20
Tester_33
    TEST_MODE = Automatic
    TEST_DESCRIPTION = ""
    BOOL_OP = OR
    TEST_CLAUSE = TEST 0 = 0
    PASSED -> XMLTemplater_7 [input 2]
    PASSED -> AttributeCreator_20
AttributeCreator_20
    ATTR_LIST = identifiant,45
    -> DuplicateRemover_13
DuplicateRemover_13
    KEYATTR = identifiant
    UNIQUE -> XMLTemplater_7 [input 1]
XMLTemplater_7
    RESULT_ATTRIBUTE = _result
    OTHER_CONSTRAINTS_INFO_QUERY_EXPR:
      <gmd:otherConstraints>
      	<gco:CharacterString>{fme:get-attribute("regime_acces_ressourceValeur")}</gco:CharacterString>
      </gmd:otherConstraints>
    ROOT_QUERY_EXPR:
      <?xml version="1.0" encoding="UTF-8"?>
      <rw:MD_Metadata xmlns:rw="http://metawal.wallonie.be/schemas/3.0" xmlns:gmd="http://www.isotc211.org/2005/gmd" xmlns:gts="http://www.isotc211.org/2005/gts" xmlns:gco="http://www.isotc211.org/2005/gco" xmlns:gml="http://www.opengis.net/gml" xmlns:geonet="http://www.fao.org/geonetwork" xmlns:xsi="http://www.w3.org/2001/XMLSchema-instance" gco:isoType="gmd:MD_Metadata" xsi:schemaLocation="http://metawal.wallonie.be/schemas/3.0 file:///H:/gimb14/c/c130606/data/schemas/rwschema.xsd">

      <gmd:MD_LegalConstraints>
      {fme:process-features("ACCESS_CONSTRAINT")}
      {fme:process-features("USECONSTRAINTS")}
      {fme:process-features("OTHER_CONSTRAINTS_INFO")}
      </gmd:MD_LegalConstraints>


      </rw:MD_Metadata>
    ACCESS_CONSTRAINT_QUERY_EXPR:
       <gmd:accessConstraints>
      				<gmd:MD_RestrictionCode codeList="http://standards.iso.org/ittf/PubliclyAvailableStandards/ISO_19139_Schemas/resources/Codelist/ML_gmxCodelists.xml#MD_RestrictionCode" codeListValue="{fme:get-attribute("regime_acces_ressourceAccessConstraints")}"/>
      </gmd:accessConstraints>
    USECONSTRAINTS_QUERY_EXPR:
      	<gmd:useConstraints>
      		<gmd:MD_RestrictionCode codeList="http://standards.iso.org/ittf/PubliclyAvailableStandards/ISO_19139_Schemas/resources/Codelist/ML_gmxCodelists.xml#MD_RestrictionCode" codeListValue="{fme:get-attribute("uselimitationsUsecConstraints")}"/>
      	</gmd:useConstraints>
    VISIBLE_QUERY_VALIDATE = Yes
    USELIMITATION_QUERY_EXPR:
      <gmd:useLimitation>
      				<gco:CharacterString>Référence légale: Text consultable à l'adresse www.gim.be</gco:CharacterString>
      </gmd:useLimitation>
    OUTPUT_XML_HEADER = Yes
    -> modif_texte_6
modif_texte_6
    _RESULT = @Value(_result)
    StringReplacer_2_Output -> XMLTemplater_2 [input 10]
    StringReplacer_2_Output -> AttributeCreator_23

Bookmark: conditions d'utilisation
synthese/conditions_utilisations (reader XLSXR_1)
    attributes: Coché char(4), UsecConstraints char(20), Partie 1 char(248), Valeur1 string, Partie 2 char(26), Valeur 2 string
    -> Tester_21
Tester_21
    TEST_MODE = Automatic
    TEST_DESCRIPTION = ""
    BOOL_OP = OR
    TEST_CLAUSE = TEST @Value(Coché) = Yes
    PASSED -> AttributeCreator_15
AttributeCreator_15
    ATTR_LIST = Valeur,@Value(Partie 1)@Value(Valeur1)@Value(Partie 2)@Value(Valeur 2)
    -> BulkAttributeRenamer_15
    -> BulkAttributeRenamer_20
BulkAttributeRenamer_20
    REPLACE_STR = uselimitations
    ATTRCHOICE = All Attributes
    PATTERN_ACTION_DISP = Add String Prefix
    -> Tester_33

Bookmark: uselimitation
synthese/uselimitations (reader XLSXR_1)
    attributes: Uselimitations string
    -> Tester_22
Tester_22
    TEST_MODE = Automatic
    TEST_DESCRIPTION = ""
    BOOL_OP = OR
    TEST_CLAUSE = TEST Uselimitations NOT_ATTRIBUTE_IS_EMPTY ""
    PASSED -> BulkAttributeRenamer_19
BulkAttributeRenamer_19
    REPLACE_STR = uselimitations_MD_Constraints
    ATTRCHOICE = All Attributes
    PATTERN_ACTION_DISP = Add String Prefix
    -> AttributeCreator_24

Bookmark: Local Code
synthese/Local_Code (reader XLSXR_1)
    attributes: id number(2,0), Valeur1 string, Valeur2 string, Valeur3 string
    -> Tester_17
Tester_17
    TEST_MODE = Automatic
    TEST_DESCRIPTION = ""
    BOOL_OP = OR
    TEST_CLAUSE = TEST @Value(id) = 2
    PASSED -> Tester_18
    FAILED -> Tester_19
Tester_18
    TEST_MODE = Automatic
    TEST_DESCRIPTION = ""
    BOOL_OP = OR
    TEST_CLAUSE = TEST Valeur1 NOT_ATTRIBUTE_IS_EMPTY ""
    PASSED -> BulkAttributeRenamer_16
    PASSED -> AttributeCreator_19
Tester_19
    TEST_MODE = Automatic
    TEST_DESCRIPTION = ""
    BOOL_OP = OR
    TEST_CLAUSE = TEST Valeur1 NOT_ATTRIBUTE_IS_EMPTY ""
    PASSED -> AttributeCreator_14
AttributeCreator_14
    ATTR_LIST = Valeur1,@Value(Valeur1)_@Value(Valeur2)_@Value(Valeur3)
    -> BulkAttributeRenamer_16
    -> AttributeCreator_19
BulkAttributeRenamer_16
    REPLACE_STR = local_code
    ATTRCHOICE = All Attributes
    PATTERN_ACTION_DISP = Add String Prefix
    -> XMLTemplater_4 [input 3]
AttributeCreator_19
    ATTR_LIST = identifiant,35
    -> DuplicateRemover_11

Bookmark: OUTPUT
XMLTemplater_2
    CONTRAINTES_QUERY_EXPR = {fme:get-attribute("_result")}
    USELIMITATION_CLASSIF_QUERY_EXPR = {fme:get-attribute("_result")}
    RESOURCECONSTRAINTS_QUERY_EXPR:
      <gmd:resourceConstraints>

       {fme:process-features("CONTRAINTES")}

      </gmd:resourceConstraints>
    ROOT_QUERY_EXPR:
      <?xml version="1.0" encoding="UTF-8"?>
      <rw:MD_Metadata xmlns:rw="http://metawal.wallonie.be/schemas/3.0" xmlns:gmd="http://www.isotc211.org/2005/gmd" xmlns:gts="http://www.isotc211.org/2005/gts" xmlns:gco="http://www.isotc211.org/2005/gco" xmlns:gml="http://www.opengis.net/gml" xmlns:geonet="http://www.fao.org/geonetwork" xmlns:xsi="http://www.w3.org/2001/XMLSchema-instance" gco:isoType="gmd:MD_Metadata" xsi:schemaLocation="http://metawal.wallonie.be/schemas/3.0 file:///H:/gimb14/c/c130606/data/schemas/rwschema.xsd">
      	<gmd:fileIdentifier>
      		<gco:CharacterString></gco:CharacterString>
      	</gmd:fileIdentifier>
      	<gmd:language>
      		<gco:CharacterString>{fme:get-attribute("metadata_lang")}</gco:CharacterString>
      	</gmd:language>
      	<gmd:characterSet>
      		<gmd:MD_CharacterSetCode codeListValue="{fme:get-attribute("characterSet")}" codeList="http://standards.iso.org/ittf/PubliclyAvailableStandards/ISO_19139_Schemas/resources/Codelist/ML_gmxCodelists.xml#MD_CharacterSetCode"/>
      	</gmd:characterSet>
        {fme:process-features("PARENT_IDENTIFIER")}
      	<gmd:hierarchyLevel>
      		<gmd:MD_ScopeCode codeList="http://standards.iso.org/ittf/PubliclyAvailableStandards/ISO_19139_Schemas/resources/Codelist/ML_gmxCodelists.xml#MD_ScopeCode" codeListValue="{fme:get-attribute("hierarchyLevel")}"/>
      	</gmd:hierarchyLevel>
          {fme:process-features("HIERARCHYLEVEL")}

      	{fme:process-features("CONTACT_METADATA")}

      	<gmd:dateStamp>
      		<gco:DateTime>{fme:get-attribute("_timestamp")}</gco:DateTime>
      	</gmd:dateStamp>
      	<gmd:metadataStandardName>
      		<gco:CharacterString>{fme:get-attribute("metadataStandardName")}</gco:CharacterString>
      	</gmd:metadataStandardName>
      	<gmd:metadataStandardVersion>
      		<gco:CharacterString>{fme:get-attribute("metadataStandardVersion")}</gco:CharacterString>
      	</gmd:metadataStandardVersion>
         	<gmd:referenceSystemInfo>
      		<gmd:MD_ReferenceSystem>
      			<gmd:referenceSystemIdentifier>
      				<gmd:RS_Identifier>
      					<gmd:code>
      						<gco:CharacterString>{fme:get-attribute("referenceSystemCode")}</gco:CharacterString>
      					</gmd:code>
      						<gmd:codeSpace>
      						<gco:CharacterString>{fme:get-attribute("CodeSpaceReferenceSystem")}</gco:CharacterString>
      					</gmd:codeSpace>
      				</gmd:RS_Identifier>
      			</gmd:referenceSystemIdentifier>
      		</gmd:MD_ReferenceSystem>
      	</gmd:referenceSystemInfo>
           {fme:process-features("EPSG")}
      	<gmd:identificationInfo>
      		<gmd:MD_DataIdentification>
      			<gmd:citation>
      				<gmd:CI_Citation>
      					<gmd:title>
      						<gco:CharacterString>{fme:get-attribute("title")}</gco:CharacterString>
      					</gmd:title>

      					{fme:process-features("ALT_T_DATES_PR_LOCAL_CODE")}



      					<gmd:identifier>
      						<gmd:RS_Identifier>

                              <gmd:code>
      								<gco:CharacterString></gco:CharacterString>
      							</gmd:code>
      							<gmd:codeSpace>
      								<gco:CharacterString>{fme:get-attribute("CodeSpace")}</gco:CharacterString>
      							</gmd:codeSpace>
      						</gmd:RS_Identifier>
      					</gmd:identifier>
      				</gmd:CI_Citation>
      			</gmd:citation>
      			<gmd:abstract>
      				<gco:CharacterString>{fme:get-attribute("abstract")}</gco:CharacterString>
      			</gmd:abstract>
      			{fme:process-features("STATUS")}


      			<gmd:pointOfContact>
      				<rw:CI_ResponsibleParty gco:isoType="gmd:CI_ResponsibleParty">
      					<gmd:organisationName>
      						<gco:CharacterString>{fme:get-attribute("organisationName_owner")}</gco:CharacterString>
      					</gmd:organisationName>
      					<gmd:contactInfo>
      						<gmd:CI_Contact>
      							<gmd:address>
      								<gmd:CI_Address>
      									<gmd:electronicMailAddress>
      										<gco:CharacterString>{fme:get-attribute("electronicMailAddress_owner")}</gco:CharacterString>
      									</gmd:electronicMailAddress>
      								</gmd:CI_Address>
      							</gmd:address>
      							<gmd:onlineResource>
      								<gmd:CI_OnlineResource>
      									<gmd:linkage>
      										<gmd:URL>{fme:get-attribute("linkage_owner")}</gmd:URL>
      									</gmd:linkage>
      									<gmd:protocol>
      										<gco:CharacterString>{fme:get-attribute("protocole_owner")}</gco:CharacterString>
      									</gmd:protocol>
      									<gmd:name>
      										<gco:CharacterString>{fme:get-attribute("name_owner")}</gco:CharacterString>
      									</gmd:name>
                                     <gmd:function>
      								<gmd:CI_OnLineFunctionCode codeList="http://standards.iso.org/ittf/PubliclyAvailableStandards/ISO_19139_Schemas/resources/Codelist/ML_gmxCodelists.xml#CI_OnLineFunctionCode" codeListValue="{fme:get-attribute("Fonction_owner")}"/>
      							</gmd:function>


      								</gmd:CI_OnlineResource>
      							</gmd:onlineResource>
      						</gmd:CI_Contact>
      					</gmd:contactInfo>
      					<gmd:role>
      						<gmd:CI_RoleCode codeListValue="{fme:get-attribute("Role_owner")}" codeList="http://standards.iso.org/ittf/PubliclyAvailableStandards/ISO_19139_Schemas/resources/Codelist/ML_gmxCodelists.xml#CI_RoleCode"/>
      					</gmd:role>
      				</rw:CI_ResponsibleParty>
                          </gmd:pointOfContact>

                     {fme:process-features("CONTACTMAINTENANCE_UPDATE")}
      			   {fme:process-features("IMAGE")}
                     {fme:process-features("KEYWORDS")}
                     {fme:process-features("RESOURCECONSTRAINTS")}
                     {fme:process-features("USELIMITATION_INFO")}
          		   {fme:process-features("USELIMITATION_CLASSIF")}
      			   {fme:process-features("SPATIALREPRESENTATION")}

      			   {fme:process-features("DENOMINATOR")}
                     {fme:process-features("DISTANCE")}



      			<gmd:language>
      				<gco:CharacterString>{fme:get-attribute("language")}</gco:CharacterString>
      			</gmd:language>
      			<gmd:characterSet>
      				<gmd:MD_CharacterSetCode codeListValue="{fme:get-attribute("characterSet")}" codeList="http://standards.iso.org/ittf/PubliclyAvailableStandards/ISO_19139_Schemas/resources/Codelist/ML_gmxCodelists.xml#MD_CharacterSetCode"/>
      			</gmd:characterSet>

      			{fme:process-features("ISO")}

      			<gmd:extent>
      				<gmd:EX_Extent>
      					<gmd:description>
      						<gco:CharacterString>{fme:get-attribute("spatialDescription")}</gco:CharacterString>
      					</gmd:description>
      					<gmd:geographicElement>
      						<gmd:EX_GeographicBoundingBox>
      							<gmd:westBoundLongitude>
      								<gco:Decimal>{fme:get-attribute("westBoundLongitude")}</gco:Decimal>
      							</gmd:westBoundLongitude>
      							<gmd:eastBoundLongitude>
      								<gco:Decimal>{fme:get-attribute("eastBoundLongitude")}</gco:Decimal>
      							</gmd:eastBoundLongitude>
      							<gmd:southBoundLatitude>
      								<gco:Decimal>{fme:get-attribute("southBoundLatitude")}</gco:Decimal>
      							</gmd:southBoundLatitude>
      							<gmd:northBoundLatitude>
      								<gco:Decimal>{fme:get-attribute("northBoundLatitude")}</gco:Decimal>
      							</gmd:northBoundLatitude>
      						</gmd:EX_GeographicBoundingBox>
      					</gmd:geographicElement>
      				</gmd:EX_Extent>
      			</gmd:extent>

          {fme:process-features("TEMPORALEXTENT")}

      		</gmd:MD_DataIdentification>
      	</gmd:identificationInfo>


           <gmd:distributionInfo>
           <gmd:MD_Distribution>
      {fme:process-features("DISTRIBUTION")}
          </gmd:MD_Distribution>
          </gmd:distributionInfo>

      	<gmd:dataQualityInfo>
      		<gmd:DQ_DataQuality>
      			<gmd:scope>
      				<gmd:DQ_Scope>
      					<gmd:level>
      						<gmd:MD_ScopeCode codeList="http://standards.iso.org/ittf/PubliclyAvailableStandards/ISO_19139_Schemas/resources/Codelist/ML_gmxCodelists.xml#MD_ScopeCode" codeListValue="{fme:get-attribute("level")}"/>
      					</gmd:level>
      				</gmd:DQ_Scope>
      			</gmd:scope>

              <gmd:report>
      				<gmd:DQ_DomainConsistency>
      					<gmd:result>
      						<gmd:DQ_ConformanceResult>
      						<gmd:specification>
      					<gmd:CI_Citation>
      						<gmd:title>
      							<gco:CharacterString>Règlement (UE) n o 1089/2010 de la Commission du 23 novembre 2010 portant modalités d'application de la directive 2007/2/CE du Parlement européen et du Conseil en ce qui concerne l'interopérabilité des séries et des services de données géographiques</gco:CharacterString>
      						</gmd:title>
      						<gmd:date>
      							<gmd:CI_Date>
      								<gmd:date>
      									<gco:Date>2010-12-08</gco:Date>
      								</gmd:date>
      								<gmd:dateType>
      									<gmd:CI_DateTypeCode codeList="http://standards.iso.org/ittf/PubliclyAvailableStandards/ISO_19139_Schemas/resources/Codelist/ML_gmxCodelists.xml#CI_DateTypeCode" codeListValue="publication">publication</gmd:CI_DateTypeCode>
      								</gmd:dateType>
      							</gmd:CI_Date>
      						</gmd:date>
      					</gmd:CI_Citation>
      				</gmd:specification>
      			         <gmd:explanation>
                                <gco:CharacterString>Veuillez consulter la spécification référencée</gco:CharacterString>
                           </gmd:explanation>
      						{fme:process-features("CONFORMANCEPASS")}
      						</gmd:DQ_ConformanceResult>
      					</gmd:result>
      				</gmd:DQ_DomainConsistency>

      			</gmd:report>
            {fme:process-features("CONFORMITE_INSPIRE")}
      			<gmd:lineage>
      				<rw:LI_Lineage gco:isoType="gmd:LI_Lineage">
      					<gmd:statement>
      						<gco:CharacterString>{fme:get-attribute("statementLineage")}</gco:CharacterString>
      					</gmd:statement>
      				</rw:LI_Lineage>
      			</gmd:lineage>
      		</gmd:DQ_DataQuality>
      	</gmd:dataQualityInfo>
      </rw:MD_Metadata>
    PARENT_IDENTIFIER_QUERY_EXPR:
         <gmd:parentIdentifier>
              <gco:CharacterString>{fme:get-attribute("parentIdentifier")}</gco:CharacterString>
          </gmd:parentIdentifier>
    VISIBLE_QUERY_VALIDATE = Yes
    USELIMITATION_INFO_QUERY_EXPR:
      <gmd:resourceConstraints>
      <gmd:MD_Constraints>
      {fme:process-features("MD_CONSTRAINTS_USELIMITATION")}
      </gmd:MD_Constraints>
      </gmd:resourceConstraints>
    CONTACTMAINTENANCE_UPDATE_QUERY_EXPR = {fme:get-attribute("_result")}
    MD_CONSTRAINTS_USELIMITATION_QUERY_EXPR:
      <gmd:useLimitation>
      <gco:CharacterString>{fme:get-attribute("uselimitations_MD_ConstraintsUselimitations")} </gco:CharacterString>
       </gmd:useLimitation>
    DISTANCE_QUERY_EXPR:
         <gmd:spatialResolution>

              <gmd:MD_Resolution>

                  <gmd:distance>

                      <gco:Distance uom="m">{fme:get-attribute("Distance_Valeur")}</gco:Distance>

                  </gmd:distance>

              </gmd:MD_Resolution>

          </gmd:spatialResolution>
    DENOMINATOR_QUERY_EXPR:
      <gmd:spatialResolution>
      				<gmd:MD_Resolution>
      					<gmd:equivalentScale>
      						<gmd:MD_RepresentativeFraction>
      							<gmd:denominator>
      								<gco:Integer>{fme:get-attribute("Denominator_Valeur")}</gco:Integer>
      							</gmd:denominator>
      						</gmd:MD_RepresentativeFraction>
      					</gmd:equivalentScale>
      				</gmd:MD_Resolution>
      			</gmd:spatialResolution>
    OUTPUT_XML_HEADER = Yes
    STATUS_QUERY_EXPR:
      	<gmd:status>
      				<gmd:MD_ProgressCode codeList="http://standards.iso.org/ittf/PubliclyAvailableStandards/ISO_19139_Schemas/resources/Codelist/ML_gmxCodelists.xml#MD_ProgressCode" codeListValue="{fme:get-attribute("status")}"/>
      			</gmd:status>
    SYST_COORD_INSPIRE1_QUERY_EXPR:
      <gmd:referenceSystemInfo>
      		<gmd:MD_ReferenceSystem>
      			<gmd:referenceSystemIdentifier>
      				<gmd:RS_Identifier>
      					<gmd:code>
      						<gco:CharacterString>http://www.opengis.net/def/crs/EPSG/0/4258</gco:CharacterString>
      					</gmd:code>
      					<gmd:codeSpace>
      						<gco:CharacterString>urn:ogc:def:crs:EPSG</gco:CharacterString>
      					</gmd:codeSpace>
      				</gmd:RS_Identifier>
      			</gmd:referenceSystemIdentifier>
      		</gmd:MD_ReferenceSystem>
      	</gmd:referenceSystemInfo>
    IMAGE_QUERY_EXPR = {fme:get-attribute("_result")}
    DISTRIBUTION_QUERY_EXPR = {fme:get-attribute("_result")}
    ISO_QUERY_EXPR:
      <gmd:topicCategory>
      				<gmd:MD_TopicCategoryCode>{fme:get-attribute("ISO_Valeur")}</gmd:MD_TopicCategoryCode>
      			</gmd:topicCategory>
    RESULT_ATTRIBUTE = text_line_data
    ALT_T_DATES_PR_LOCAL_CODE_QUERY_EXPR = {fme:get-attribute("_result")}
    KEYWORDS_QUERY_EXPR = {fme:get-attribute("_result")}
    SPATIALREPRESENTATION_QUERY_EXPR:
      	<gmd:spatialRepresentationType>
      				<gmd:MD_SpatialRepresentationTypeCode codeListValue="{fme:get-attribute("spatialRepresentationType")}" codeList="http://standards.iso.org/ittf/PubliclyAvailableStandards/ISO_19139_Schemas/resources/Codelist/ML_gmxCodelists.xml#MD_SpatialRepresentationTypeCode"/>
      			</gmd:spatialRepresentationType>
    CONFORMITE_INSPIRE_QUERY_EXPR:
       <gmd:report>
                  <gmd:DQ_DomainConsistency>
                     <gmd:measureIdentification>
                        <gmd:RS_Identifier>
                           <gmd:code gco:nilReason="missing">
                              <gco:CharacterString/>
                           </gmd:code>
                           <gmd:codeSpace gco:nilReason="missing">
                              <gco:CharacterString/>
                           </gmd:codeSpace>
                        </gmd:RS_Identifier>
                     </gmd:measureIdentification>
                     <gmd:measureDescription>
                        <gco:CharacterString>Conformité du jeu de données au modèle de données {fme:get-attribute("inspire_Nom")} d'INSPIRE</gco:CharacterString>
                     </gmd:measureDescription>
                     <gmd:dateTime gco:nilReason="missing"/>
                     <gmd:result>
                        <gmd:DQ_ConformanceResult>
                           <gmd:specification>
                              <gmd:CI_Citation>
                                 <gmd:title>
                                    <gco:CharacterString>{fme:get-attribute("inspire_Traduction")}</gco:CharacterString>
                                 </gmd:title>
                                 <gmd:date>
                                    <gmd:CI_Date>
                                       <gmd:date>
                                          <gco:Date>{fme:get-attribute("inspire_Date")}</gco:Date>
                                       </gmd:date>
                                       <gmd:dateType>
                                          <gmd:CI_DateTypeCode codeList="http://standards.iso.org/ittf/PubliclyAvailableStandards/ISO_19139_Schemas/resources/Codelist/ML_gmxCodelists.xml#CI_DateTypeCode"
                                                               codeListValue="publication"/>
                                       </gmd:dateType>
                                    </gmd:CI_Date>
                                 </gmd:date>
                              </gmd:CI_Citation>
                           </gmd:specification>
                           <gmd:explanation>
                                <gco:CharacterString>{fme:get-attribute("inspire_conformanceExplanation")}</gco:CharacterString>
                           </gmd:explanation>
                           <gmd:pass><gco:Boolean>{fme:get-attribute("inspire_Conforme au thème")}</gco:Boolean></gmd:pass>
                        </gmd:DQ_ConformanceResult>
                     </gmd:result>
                  </gmd:DQ_DomainConsistency>
             </gmd:report>
    HIERARCHYLEVEL_QUERY_EXPR:
      <gmd:hierarchyLevelName>
      		<gco:CharacterString>Séries de jeux de données</gco:CharacterString>
      	</gmd:hierarchyLevelName>
    CONTACT_METADATA_QUERY_EXPR = {fme:get-attribute("_result")}
    TEMPORALEXTENT_QUERY_EXPR = {fme:get-attribute("_result")}
    CONFORMANCEPASS_QUERY_EXPR = {fme:get-attribute("_result")}
    EPSG_QUERY_EXPR:
      <gmd:referenceSystemInfo>
      		<gmd:MD_ReferenceSystem>
      			<gmd:referenceSystemIdentifier>
      				<gmd:RS_Identifier>
      					<gmd:code>
      						<gco:CharacterString>http://www.opengis.net/def/crs/EPSG/0/4258</gco:CharacterString>
      					</gmd:code>
      					<gmd:codeSpace>
      						<gco:CharacterString>urn:ogc:def:crs:EPSG</gco:CharacterString>
      					</gmd:codeSpace>
      				</gmd:RS_Identifier>
      			</gmd:referenceSystemIdentifier>
      		</gmd:MD_ReferenceSystem>
      	</gmd:referenceSystemInfo>
    -> StringReplacer
StringReplacer
    SRC_ATTRS = text_line_data
    REGEXP = no
    CASE = no
    REPLACE_TEXT = <
    NO_MATCH = _FME_NO_OP_
    FIND_TEXT = &lt;
    -> StringReplacer_2
StringReplacer_2
    SRC_ATTRS = text_line_data
    REGEXP = no
    CASE = no
    REPLACE_TEXT = >
    NO_MATCH = _FME_NO_OP_
    FIND_TEXT = &gt;
    -> FilenamePartExtractor
FilenamePartExtractor
    SRC_ATTR = $(SourceDataset_XLSXR_3)
    ROOTNAME_ATTR = nom_fichier
    -> text_line (writer TEXTLINE_1)
text_line (writer TEXTLINE_1)
    attributes: text_line_data buffer

FME custom transformer DISTRIBUTIONACCESLIMITEDOC

Parameters:
- DISTRIBUTIONACCESLIMITE_DIRSTRIBUTIONURLAPP = @Value(Distributionacceslimite_dirstributionURLApp)   # Distributionacceslimite Dirstributionurlapp
- DISTRIBUTIONACCESLIMITE_DISTRIBUTIONPROTOCOLAPP = @Value(Distributionacceslimite_distributionProtocolApp)   # Distributionacceslimite Distributionprotocolapp
- DISTRIBUTIONACCESLIMITE_DISTRIBUTIONNAMEAPP = @Value(Distributionacceslimite_distributionNameApp)   # Distributionacceslimite Distributionnameapp
- DISTRIBUTIONACCESLIMITE_DISTRIBUTIONDESCRIPTIOAPP = @Value(Distributionacceslimite_distributionDescriptioApp)   # Distributionacceslimite Distributiondescriptioapp
- DISTRIBUTIONACCESLIMITE_DISTRIBUTIONFUNCTIOAPP = @Value(Distributionacceslimite_distributionFunctioApp)   # Distributionacceslimite Distributionfunctioapp
- DISTRIBUTIONACCESLIMITE_ELEMENT_ISO = @Value(Distributionacceslimite_Element_ISO)   # Distributionacceslimite Element Iso
- _COUNT = @Value(_count)   # Count

Input (input)
    -> dirstributionURLApp
    -> distributionProtocolApp
    -> distributionNameApp
    -> distributionDescriptioApp
    -> distributionFunctioApp
dirstributionURLApp: Tester
    TEST_MODE = Automatic
    TEST_DESCRIPTION = ""
    BOOL_OP = AND
    TEST_CLAUSE:
      TEST Distributionacceslimite_dirstributionURLApp NOT_ATTRIBUTE_VALUE_NULL ""
      TEST Distributionacceslimite_dirstributionURLApp NOT_ATTRIBUTE_IS_EMPTY ""
      TEST Distributionacceslimite_dirstributionURLApp NOT_ATTRIBUTE_IS_MISSING ""
    PASSED -> DuplicateRemover
    PASSED -> XMLTemplater [input 2]
distributionProtocolApp: Tester
    TEST_MODE = Automatic
    TEST_DESCRIPTION = ""
    BOOL_OP = AND
    TEST_CLAUSE:
      TEST Distributionacceslimite_distributionProtocolApp NOT_ATTRIBUTE_VALUE_NULL ""
      TEST Distributionacceslimite_distributionProtocolApp NOT_ATTRIBUTE_IS_EMPTY ""
      TEST Distributionacceslimite_distributionProtocolApp NOT_ATTRIBUTE_IS_MISSING ""
    PASSED -> DuplicateRemover
    PASSED -> XMLTemplater [input 3]
distributionNameApp: Tester
    TEST_MODE = Automatic
    TEST_DESCRIPTION = ""
    BOOL_OP = AND
    TEST_CLAUSE:
      TEST Distributionacceslimite_distributionNameApp NOT_ATTRIBUTE_VALUE_NULL ""
      TEST Distributionacceslimite_distributionNameApp NOT_ATTRIBUTE_IS_EMPTY ""
      TEST Distributionacceslimite_distributionNameApp NOT_ATTRIBUTE_IS_MISSING ""
    PASSED -> DuplicateRemover
    PASSED -> XMLTemplater [input 4]
distributionDescriptioApp: Tester
    TEST_MODE = Automatic
    TEST_DESCRIPTION = ""
    BOOL_OP = AND
    TEST_CLAUSE:
      TEST Distributionacceslimite_distributionDescriptioApp NOT_ATTRIBUTE_VALUE_NULL ""
      TEST Distributionacceslimite_distributionDescriptioApp NOT_ATTRIBUTE_IS_EMPTY ""
      TEST Distributionacceslimite_distributionDescriptioApp NOT_ATTRIBUTE_IS_MISSING ""
    PASSED -> DuplicateRemover
    PASSED -> XMLTemplater [input 5]
DuplicateRemover
    KEYATTR = _count
    UNIQUE -> XMLTemplater [input 1]
distributionFunctioApp: Tester
    TEST_MODE = Automatic
    TEST_DESCRIPTION = ""
    BOOL_OP = AND
    TEST_CLAUSE:
      TEST Distributionacceslimite_distributionFunctioApp NOT_ATTRIBUTE_VALUE_NULL ""
      TEST Distributionacceslimite_distributionFunctioApp NOT_ATTRIBUTE_IS_EMPTY ""
      TEST Distributionacceslimite_distributionFunctioApp NOT_ATTRIBUTE_IS_MISSING ""
    PASSED -> XMLTemplater [input 6]
XMLTemplater
    GROUP_BY = _count
    RESULT_ATTRIBUTE = _result
    DIRSTRIBUTIONURLAPP_QUERY_EXPR:
      <gmd:linkage>
      		<gmd:URL>{fme:get-attribute("Distributionacceslimite_dirstributionURLApp")}</gmd:URL>
      </gmd:linkage>
    DISTRIBUTIONFUNCTIOAPP_QUERY_EXPR:
      <gmd:function>
      			<gmd:CI_OnLineFunctionCode codeList="http://standards.iso.org/ittf/PubliclyAvailableStandards/ISO_19139_Schemas/resources/Codelist/ML_gmxCodelists.xml#CI_OnLineFunctionCode" codeListValue="{fme:get-attribute("Distributionacceslimite_distributionFunctioApp")}"/>
      </gmd:function>
    CONSECUTIVE_GROUPS = No
    DISTRIBUTIONNAMEAPP_QUERY_EXPR:
      <gmd:name>
      		<gco:CharacterString>{fme:get-attribute("Distributionacceslimite_distributionNameApp")}</gco:CharacterString>
      </gmd:name>
    ROOT_QUERY_EXPR:
      <?xml version="1.0" encoding="UTF-8"?>
      <rw:MD_Metadata xmlns:rw="http://metawal.wallonie.be/schemas/3.0" xmlns:gmd="http://www.isotc211.org/2005/gmd" xmlns:gts="http://www.isotc211.org/2005/gts" xmlns:gco="http://www.isotc211.org/2005/gco" xmlns:gml="http://www.opengis.net/gml" xmlns:geonet="http://www.fao.org/geonetwork" xmlns:xsi="http://www.w3.org/2001/XMLSchema-instance" gco:isoType="gmd:MD_Metadata" xsi:schemaLocation="http://metawal.wallonie.be/schemas/3.0 file:///H:/gimb14/c/c130606/data/schemas/rwschema.xsd">
      <gmd:transferOptions>
      				<gmd:MD_DigitalTransferOptions>
      					<gmd:onLine>
      						<gmd:CI_OnlineResource>
      							{fme:process-features("DIRSTRIBUTIONURLAPP")}
      							{fme:process-features("DISTRIBUTIONPROTOCOLAPP")}
      							{fme:process-features("DISTRIBUTIONNAMEAPP")}
      							{fme:process-features("DISTRIBUTIONDESCRIPTIOAPP")}
                                {fme:process-features("DISTRIBUTIONFUNCTIOAPP")}
      						</gmd:CI_OnlineResource>
      					</gmd:onLine>
      					</gmd:MD_DigitalTransferOptions>
      			</gmd:transferOptions>


      </rw:MD_Metadata>
    DISTRIBUTIONPROTOCOLAPP_QUERY_EXPR:
      <gmd:protocol gco:nilReason="missing">
      		<gco:CharacterString>{fme:get-attribute("Distributionacceslimite_distributionProtocolApp")}</gco:CharacterString>
      </gmd:protocol>
    DISTRIBUTIONDESCRIPTIOAPP_QUERY_EXPR:
      <gmd:description>
      			<gco:CharacterString>{fme:get-attribute("Distributionacceslimite_distributionDescriptioApp")}</gco:CharacterString>
      </gmd:description>
    VISIBLE_QUERY_VALIDATE = Yes
    OUTPUT_XML_HEADER = Yes
    -> Output (output)
Output (output)

FME custom transformer distri_offline

Parameters:
- DISTRIBUTIONONLINE_DISTRIBUTEUR = @Value(Distributiononline_Distributeur)   # Distributiononline Distributeur
- DISTRIBUTIONONLINE_ORDERINGINSTRUCTIONS1 = @Value(Distributiononline_orderingInstructions1)   # Distributiononline Orderinginstructions1
- DISTRIBUTIONONLINE_NAMEFORMAT1 = @Value(Distributiononline_nameformat1)   # Distributiononline Nameformat1
- DISTRIBUTIONONLINE_VERSIONFORMAT1 = @Value(Distributiononline_versionFormat1)   # Distributiononline Versionformat1
- DISTRIBUTIONONLINE_TRANSFERSIZE1__CRÉER_BLOC_XML_ = @Value(Distributiononline_transfersize1 (créer bloc xml))   # Distributiononline Transfersize1 (créer bloc xml)
- DISTRIBUTIONONLINE_DIRSTRIBUTIONURLDL = @Value(Distributiononline_dirstributionURLdl)   # Distributiononline Dirstributionurldl
- DISTRIBUTIONONLINE_DISTRIBUTIONPROTOCOLDL = @Value(Distributiononline_distributionProtocoldl)   # Distributiononline Distributionprotocoldl
- DISTRIBUTIONONLINE_DISTRIBUTIONNAMEDL = @Value(Distributiononline_distributionNamedl)   # Distributiononline Distributionnamedl
- DISTRIBUTIONONLINE_DISTRIBUTIONDESCRIPTIODL = @Value(Distributiononline_distributionDescriptiodl)   # Distributiononline Distributiondescriptiodl
- DISTRIBUTIONONLINE_DISTRIBUTIONFUNCTIODL = @Value(Distributiononline_distributionFunctiodl)   # Distributiononline Distributionfunctiodl
- DISTRIBUTIONONLINE_ELEMENT_ISO = @Value(Distributiononline_Element_ISO)   # Distributiononline Element Iso
- DISTRIBUTIONONLINE_ROLE = @Value(Distributiononline_Role)   # Distributiononline Role
- DISTRIBUTIONONLINE_ORGANISATIONNAME = @Value(Distributiononline_organisationName)   # Distributiononline Organisationname
- DISTRIBUTIONONLINE_ELECTRONICMAILADDRESS = @Value(Distributiononline_electronicMailAddress)   # Distributiononline Electronicmailaddress
- DISTRIBUTIONONLINE_INDIVIDUALNAME = @Value(Distributiononline_individualName)   # Distributiononline Individualname
- DISTRIBUTIONONLINE_POSITIONNAME = @Value(Distributiononline_positionName)   # Distributiononline Positionname
- DISTRIBUTIONONLINE_VOICE = @Value(Distributiononline_voice)   # Distributiononline Voice
- DISTRIBUTIONONLINE_DELIVERYPOINT = @Value(Distributiononline_deliveryPoint)   # Distributiononline Deliverypoint
- DISTRIBUTIONONLINE_CITY = @Value(Distributiononline_city)   # Distributiononline City
- DISTRIBUTIONONLINE_POSTALCODE = @Value(Distributiononline_postalCode)   # Distributiononline Postalcode
- DISTRIBUTIONONLINE_COUNTRY = @Value(Distributiononline_country)   # Distributiononline Country
- DISTRIBUTIONONLINE_LINKAGE = @Value(Distributiononline_linkage)   # Distributiononline Linkage
- DISTRIBUTIONONLINE_PROTOCOLE = @Value(Distributiononline_protocole)   # Distributiononline Protocole
- DISTRIBUTIONONLINE_NAME = @Value(Distributiononline_name)   # Distributiononline Name
- DISTRIBUTIONONLINE_DESCRIPTION = @Value(Distributiononline_description)   # Distributiononline Description
- DISTRIBUTIONONLINE_FUNCTION = @Value(Distributiononline_function)   # Distributiononline Function
- DISTRIBUTIONONLINE_ROLE_TYPE = @Value(Distributiononline_Role_type)   # Distributiononline Role Type
- DISTRIBUTIONONLINE__ELEMENT_INDEX = @Value(Distributiononline__element_index)   # Distributiononline Element Index
- DISTRIBUTIONONLINE__COUNT = @Value(Distributiononline__count)   # Distributiononline Count
- DISTRIBUTIONONLINE_MEDIUMNAME = @Value(Distributiononline_mediumName)   # Distributiononline Mediumname
- DISTRIBUTIONONLINE_MEDIUMNAMECODE = @Value(Distributiononline_mediumNameCode)   # Distributiononline Mediumnamecode
- DISTRIBUTIONONLINE_DISTRIBUTEUR_2 = @Value(Distributiononline_Distributeur)   # Distributiononline Distributeur
- DISTRIBUTIONONLINE_ORDERINGINSTRUCTIONS3 = @Value(Distributiononline_orderingInstructions3)   # Distributiononline Orderinginstructions3
- DISTRIBUTIONONLINE_NAMEFORMAT3 = @Value(Distributiononline_nameformat3)   # Distributiononline Nameformat3
- DISTRIBUTIONONLINE_VERSIONFORMAT3 = @Value(Distributiononline_versionFormat3)   # Distributiononline Versionformat3
- DISTRIBUTIONONLINE_TRANSFERSIZE3__CRÉER_BLOC_XML_ = @Value(Distributiononline_transfersize3 (créer bloc xml))   # Distributiononline Transfersize3 (créer bloc xml)
- DISTRIBUTIONONLINE_MEDIUMNAME_2 = @Value(Distributiononline_mediumName)   # Distributiononline Mediumname
- DISTRIBUTIONONLINE_MEDIUMNAMECODE_2 = @Value(Distributiononline_mediumNameCode)   # Distributiononline Mediumnamecode
- DISTRIBUTIONONLINE__COUNT_2 = @Value(Distributiononline__count)   # Distributiononline Count

Tester_39_Input (input)
    -> Tester
Tester
    TEST_MODE = Automatic
    TEST_DESCRIPTION = ""
    BOOL_OP = AND
    TEST_CLAUSE:
      TEST Distributiononline_Distributeur NOT_ATTRIBUTE_VALUE_NULL ""
      TEST Distributiononline_Distributeur NOT_ATTRIBUTE_IS_EMPTY ""
      TEST Distributiononline_Distributeur NOT_ATTRIBUTE_IS_MISSING ""
    PASSED -> medium_name_code
    PASSED -> ordering_instruction
    PASSED -> nameformat
    PASSED -> medium_name
    PASSED -> DuplicateRemover_2
    PASSED -> AttributeRenamer
    PASSED -> versionformat
ordering_instruction: Tester
    TEST_MODE = Automatic
    TEST_DESCRIPTION = ""
    BOOL_OP = AND
    TEST_CLAUSE:
      TEST Distributiononline_orderingInstructions3 NOT_ATTRIBUTE_VALUE_NULL ""
      TEST Distributiononline_orderingInstructions3 NOT_ATTRIBUTE_IS_EMPTY ""
      TEST Distributiononline_orderingInstructions3 NOT_ATTRIBUTE_IS_MISSING ""
    PASSED -> XMLTemplater [input 2]
    PASSED -> DuplicateRemover_2
nameformat: Tester
    TEST_MODE = Automatic
    TEST_DESCRIPTION = ""
    BOOL_OP = AND
    TEST_CLAUSE:
      TEST Distributiononline_nameformat3 NOT_ATTRIBUTE_VALUE_NULL ""
      TEST Distributiononline_nameformat3 NOT_ATTRIBUTE_IS_EMPTY ""
      TEST Distributiononline_nameformat3 NOT_ATTRIBUTE_IS_MISSING ""
    PASSED -> XMLTemplater [input 9]
    PASSED -> DuplicateRemover
    PASSED -> DuplicateRemover_2
versionformat: Tester
    TEST_MODE = Automatic
    TEST_DESCRIPTION = ""
    BOOL_OP = AND
    TEST_CLAUSE:
      TEST Distributiononline_versionFormat3 NOT_ATTRIBUTE_VALUE_NULL ""
      TEST Distributiononline_versionFormat3 NOT_ATTRIBUTE_IS_EMPTY ""
      TEST Distributiononline_versionFormat3 NOT_ATTRIBUTE_IS_MISSING ""
    PASSED -> XMLTemplater [input 10]
    PASSED -> DuplicateRemover
    PASSED -> DuplicateRemover_2
DuplicateRemover
    KEYATTR = Distributiononline__count
    UNIQUE -> XMLTemplater [input 8]
AttributeRenamer
    ATTR_LIST = "Distributiononline_transfersize3 (créer bloc xml)",Distribution_transfersize,""
    -> transfersize
transfersize: Tester
    TEST_MODE = Automatic
    TEST_DESCRIPTION = ""
    BOOL_OP = AND
    TEST_CLAUSE:
      TEST Distribution_transfersize NOT_ATTRIBUTE_VALUE_NULL ""
      TEST Distribution_transfersize NOT_ATTRIBUTE_IS_EMPTY ""
      TEST Distribution_transfersize NOT_ATTRIBUTE_IS_MISSING ""
    PASSED -> DuplicateRemover_2
    PASSED -> DuplicateRemover_3
    PASSED -> XMLTemplater [input 6]
DuplicateRemover_2
    KEYATTR = Distributiononline__count
    UNIQUE -> XMLTemplater [input 1]
medium_name: Tester
    TEST_MODE = Automatic
    TEST_DESCRIPTION = ""
    BOOL_OP = AND
    TEST_CLAUSE:
      TEST Distributiononline_mediumName NOT_ATTRIBUTE_VALUE_NULL ""
      TEST Distributiononline_mediumName NOT_ATTRIBUTE_IS_EMPTY ""
      TEST Distributiononline_mediumName NOT_ATTRIBUTE_IS_MISSING ""
    PASSED -> XMLTemplater [input 4]
    PASSED -> DuplicateRemover_4
    PASSED -> DuplicateRemover_3
medium_name_code: Tester
    TEST_MODE = Automatic
    TEST_DESCRIPTION = ""
    BOOL_OP = AND
    TEST_CLAUSE:
      TEST Distributiononline_mediumNameCode NOT_ATTRIBUTE_VALUE_NULL ""
      TEST Distributiononline_mediumNameCode NOT_ATTRIBUTE_IS_EMPTY ""
      TEST Distributiononline_mediumNameCode NOT_ATTRIBUTE_IS_MISSING ""
    PASSED -> XMLTemplater [input 3]
    PASSED -> DuplicateRemover_4
    PASSED -> DuplicateRemover_3
DuplicateRemover_3
    KEYATTR = Distributiononline__count
    UNIQUE -> XMLTemplater [input 5]
DuplicateRemover_4
    KEYATTR = Distributiononline__count
    UNIQUE -> XMLTemplater [input 7]
XMLTemplater
    GROUP_BY = Distributiononline__count
    ORDERINGINSTRUCTIONS_QUERY_EXPR:
      <gmd:distributionOrderProcess>
      						<gmd:MD_StandardOrderProcess>
      							<gmd:orderingInstructions>
      								<gco:CharacterString>{fme:get-attribute("Distributiononline_orderingInstructions3")}</gco:CharacterString>
      							</gmd:orderingInstructions>
      						</gmd:MD_StandardOrderProcess>
      </gmd:distributionOrderProcess>
    RESULT_ATTRIBUTE = _result
    TRANSFERSIZE_QUERY_EXPR:
      	<gmd:transferSize>
      				<gco:Real>{fme:get-attribute("Distribution_transfersize")}</gco:Real>
      	</gmd:transferSize>
    OFFLINERESSOURCE_QUERY_EXPR:
      	<gmd:offLine>
      				<gmd:MD_Medium>
      					{fme:process-features("MEDIUMNAMECODE")}
      				{fme:process-features("MEDIUMNAME")}
      				</gmd:MD_Medium>
      			</gmd:offLine>
    DISTRUBUTIONFORMAT_INFO_QUERY_EXPR:
      			<gmd:distributorFormat>
      				<gmd:MD_Format>
      				{fme:process-features("NAMEFORMAT")}
      				{fme:process-features("VERSIONFORMAT")}
      				</gmd:MD_Format>
      			</gmd:distributorFormat>
    MEDIUMNAMECODE_QUERY_EXPR:
      <gmd:name>
      		<gmd:MD_MediumNameCode codeList=" http://standards.iso.org/ittf/PubliclyAvailableStandards/ISO_19139_Schemas/resources/codelist/gmxCodelists.xml#MD_MediumNameCode" codeListValue="{fme:get-attribute("Distributiononline_mediumNameCode")}"/>
      </gmd:name>
    NAMEFORMAT_QUERY_EXPR:
      <gmd:name>
      		<gco:CharacterString>{fme:get-attribute("Distributiononline_nameformat3")}</gco:CharacterString>
      </gmd:name>
    MEDIUMNAME_QUERY_EXPR:
      <gmd:mediumNote>
      		<gco:CharacterString>{fme:get-attribute("Distributiononline_mediumName")}</gco:CharacterString>
      </gmd:mediumNote>
    CONSECUTIVE_GROUPS = No
    ROOT_QUERY_EXPR:
          <?xml version="1.0" encoding="UTF-8"?>
      <rw:MD_Metadata xmlns:rw="http://metawal.wallonie.be/schemas/3.0" xmlns:gmd="http://www.isotc211.org/2005/gmd" xmlns:gts="http://www.isotc211.org/2005/gts" xmlns:gco="http://www.isotc211.org/2005/gco" xmlns:gml="http://www.opengis.net/gml" xmlns:geonet="http://www.fao.org/geonetwork" xmlns:xsi="http://www.w3.org/2001/XMLSchema-instance" gco:isoType="gmd:MD_Metadata" xsi:schemaLocation="http://metawal.wallonie.be/schemas/3.0 file:///H:/gimb14/c/c130606/data/schemas/rwschema.xsd">
      {fme:process-features("ORDERINGINSTRUCTIONS")}
      {fme:process-features("DISTRUBUTIONFORMAT_INFO")}
      {fme:process-features("TRANSFEROPTION")}


      </rw:MD_Metadata>
    VERSIONFORMAT_QUERY_EXPR:
      <gmd:version>
      		<gco:CharacterString>{fme:get-attribute("Distributiononline_versionFormat3")}</gco:CharacterString>
      </gmd:version>
    VISIBLE_QUERY_VALIDATE = Yes
    TRANSFEROPTION_QUERY_EXPR:
      		<gmd:distributorTransferOptions>
      				<gmd:MD_DigitalTransferOptions>
      			{fme:process-features("TRANSFERSIZE")}
                {fme:process-features("OFFLINERESSOURCE")}
      					</gmd:MD_DigitalTransferOptions>
      			</gmd:distributorTransferOptions>
    OUTPUT_XML_HEADER = Yes
    -> Tester_39_Passed (output)
Tester_39_Passed (output)

FME custom transformer distri_online

Parameters:
- DISTRIBUTIONONLINE_DISTRIBUTEUR = @Value(Distributiononline_Distributeur)   # Distributiononline Distributeur
- DISTRIBUTIONONLINE_ORDERINGINSTRUCTIONS1 = @Value(Distributiononline_orderingInstructions1)   # Distributiononline Orderinginstructions1
- DISTRIBUTIONONLINE_NAMEFORMAT1 = @Value(Distributiononline_nameformat1)   # Distributiononline Nameformat1
- DISTRIBUTIONONLINE_VERSIONFORMAT1 = @Value(Distributiononline_versionFormat1)   # Distributiononline Versionformat1
- DISTRIBUTIONONLINE_TRANSFERSIZE1__CRÉER_BLOC_XML_ = @Value(Distributiononline_transfersize1 (créer bloc xml))   # Distributiononline Transfersize1 (créer bloc xml)
- DISTRIBUTIONONLINE_DIRSTRIBUTIONURLDL = @Value(Distributiononline_dirstributionURLdl)   # Distributiononline Dirstributionurldl
- DISTRIBUTIONONLINE_DISTRIBUTIONPROTOCOLDL = @Value(Distributiononline_distributionProtocoldl)   # Distributiononline Distributionprotocoldl
- DISTRIBUTIONONLINE_DISTRIBUTIONNAMEDL = @Value(Distributiononline_distributionNamedl)   # Distributiononline Distributionnamedl
- DISTRIBUTIONONLINE_DISTRIBUTIONDESCRIPTIODL = @Value(Distributiononline_distributionDescriptiodl)   # Distributiononline Distributiondescriptiodl
- DISTRIBUTIONONLINE_DISTRIBUTIONFUNCTIODL = @Value(Distributiononline_distributionFunctiodl)   # Distributiononline Distributionfunctiodl
- DISTRIBUTIONONLINE_ELEMENT_ISO = @Value(Distributiononline_Element_ISO)   # Distributiononline Element Iso
- DISTRIBUTIONONLINE_ROLE = @Value(Distributiononline_Role)   # Distributiononline Role
- DISTRIBUTIONONLINE_ORGANISATIONNAME = @Value(Distributiononline_organisationName)   # Distributiononline Organisationname
- DISTRIBUTIONONLINE_ELECTRONICMAILADDRESS = @Value(Distributiononline_electronicMailAddress)   # Distributiononline Electronicmailaddress
- DISTRIBUTIONONLINE_INDIVIDUALNAME = @Value(Distributiononline_individualName)   # Distributiononline Individualname
- DISTRIBUTIONONLINE_POSITIONNAME = @Value(Distributiononline_positionName)   # Distributiononline Positionname
- DISTRIBUTIONONLINE_VOICE = @Value(Distributiononline_voice)   # Distributiononline Voice
- DISTRIBUTIONONLINE_DELIVERYPOINT = @Value(Distributiononline_deliveryPoint)   # Distributiononline Deliverypoint
- DISTRIBUTIONONLINE_CITY = @Value(Distributiononline_city)   # Distributiononline City
- DISTRIBUTIONONLINE_POSTALCODE = @Value(Distributiononline_postalCode)   # Distributiononline Postalcode
- DISTRIBUTIONONLINE_COUNTRY = @Value(Distributiononline_country)   # Distributiononline Country
- DISTRIBUTIONONLINE_LINKAGE = @Value(Distributiononline_linkage)   # Distributiononline Linkage
- DISTRIBUTIONONLINE_PROTOCOLE = @Value(Distributiononline_protocole)   # Distributiononline Protocole
- DISTRIBUTIONONLINE_NAME = @Value(Distributiononline_name)   # Distributiononline Name
- DISTRIBUTIONONLINE_DESCRIPTION = @Value(Distributiononline_description)   # Distributiononline Description
- DISTRIBUTIONONLINE_FUNCTION = @Value(Distributiononline_function)   # Distributiononline Function
- DISTRIBUTIONONLINE_ROLE_TYPE = @Value(Distributiononline_Role_type)   # Distributiononline Role Type
- DISTRIBUTIONONLINE__ELEMENT_INDEX = @Value(Distributiononline__element_index)   # Distributiononline Element Index
- DISTRIBUTIONONLINE__COUNT = @Value(Distributiononline__count)   # Distributiononline Count

Tester_39_Input (input)
    -> ordering_instruction
    -> nameformat
    -> versionformat
    -> dirstributionURLdl
    -> distributionProtocoldl
    -> distributionNamedl
    -> distributionDescriptiodl
    -> distributionFunctiodl
    -> AttributeRenamer
ordering_instruction: Tester
    TEST_MODE = Automatic
    TEST_DESCRIPTION = ""
    BOOL_OP = AND
    TEST_CLAUSE:
      TEST Distributiononline_orderingInstructions1 NOT_ATTRIBUTE_VALUE_NULL ""
      TEST Distributiononline_orderingInstructions1 NOT_ATTRIBUTE_IS_EMPTY ""
      TEST Distributiononline_orderingInstructions1 NOT_ATTRIBUTE_IS_MISSING ""
    PASSED -> XMLTemplater [input 2]
    PASSED -> DuplicateRemover_2
nameformat: Tester
    TEST_MODE = Automatic
    TEST_DESCRIPTION = ""
    BOOL_OP = AND
    TEST_CLAUSE:
      TEST Distributiononline_nameformat1 NOT_ATTRIBUTE_VALUE_NULL ""
      TEST Distributiononline_nameformat1 NOT_ATTRIBUTE_IS_EMPTY ""
      TEST Distributiononline_nameformat1 NOT_ATTRIBUTE_IS_MISSING ""
    PASSED -> XMLTemplater [input 12]
    PASSED -> DuplicateRemover
    PASSED -> DuplicateRemover_2
versionformat: Tester
    TEST_MODE = Automatic
    TEST_DESCRIPTION = ""
    BOOL_OP = AND
    TEST_CLAUSE:
      TEST Distributiononline_versionFormat1 NOT_ATTRIBUTE_VALUE_NULL ""
      TEST Distributiononline_versionFormat1 NOT_ATTRIBUTE_IS_EMPTY ""
      TEST Distributiononline_versionFormat1 NOT_ATTRIBUTE_IS_MISSING ""
    PASSED -> XMLTemplater [input 13]
    PASSED -> DuplicateRemover
    PASSED -> DuplicateRemover_2
DuplicateRemover
    KEYATTR = Distributiononline__count
    UNIQUE -> XMLTemplater [input 11]
AttributeRenamer
    ATTR_LIST = "Distributiononline_transfersize1 (créer bloc xml)",Distribution_transfersize,""
    -> transfersize
transfersize: Tester
    TEST_MODE = Automatic
    TEST_DESCRIPTION = ""
    BOOL_OP = AND
    TEST_CLAUSE:
      TEST Distribution_transfersize NOT_ATTRIBUTE_VALUE_NULL ""
      TEST Distribution_transfersize NOT_ATTRIBUTE_IS_EMPTY ""
      TEST Distribution_transfersize NOT_ATTRIBUTE_IS_MISSING ""
    PASSED -> DuplicateRemover_2
    PASSED -> DuplicateRemover_3
    PASSED -> XMLTemplater [input 4]
dirstributionURLdl: Tester
    TEST_MODE = Automatic
    TEST_DESCRIPTION = ""
    BOOL_OP = AND
    TEST_CLAUSE:
      TEST Distributiononline_dirstributionURLdl NOT_ATTRIBUTE_VALUE_NULL ""
      TEST Distributiononline_dirstributionURLdl NOT_ATTRIBUTE_IS_EMPTY ""
      TEST Distributiononline_dirstributionURLdl NOT_ATTRIBUTE_IS_MISSING ""
    PASSED -> XMLTemplater [input 5]
    PASSED -> DuplicateRemover_2
    PASSED -> DuplicateRemover_4
    PASSED -> DuplicateRemover_3
distributionProtocoldl: Tester
    TEST_MODE = Automatic
    TEST_DESCRIPTION = ""
    BOOL_OP = AND
    TEST_CLAUSE:
      TEST Distributiononline_distributionProtocoldl NOT_ATTRIBUTE_VALUE_NULL ""
      TEST Distributiononline_distributionProtocoldl NOT_ATTRIBUTE_IS_EMPTY ""
      TEST Distributiononline_distributionProtocoldl NOT_ATTRIBUTE_IS_MISSING ""
    PASSED -> XMLTemplater [input 6]
    PASSED -> DuplicateRemover_2
    PASSED -> DuplicateRemover_4
    PASSED -> DuplicateRemover_3
distributionNamedl: Tester
    TEST_MODE = Automatic
    TEST_DESCRIPTION = ""
    BOOL_OP = AND
    TEST_CLAUSE:
      TEST Distributiononline_distributionNamedl NOT_ATTRIBUTE_VALUE_NULL ""
      TEST Distributiononline_distributionNamedl NOT_ATTRIBUTE_IS_EMPTY ""
      TEST Distributiononline_distributionNamedl NOT_ATTRIBUTE_IS_MISSING ""
    PASSED -> XMLTemplater [input 7]
    PASSED -> DuplicateRemover_2
    PASSED -> DuplicateRemover_4
    PASSED -> DuplicateRemover_3
distributionDescriptiodl: Tester
    TEST_MODE = Automatic
    TEST_DESCRIPTION = ""
    BOOL_OP = AND
    TEST_CLAUSE:
      TEST Distributiononline_distributionNamedl NOT_ATTRIBUTE_VALUE_NULL ""
      TEST Distributiononline_distributionNamedl NOT_ATTRIBUTE_IS_EMPTY ""
      TEST Distributiononline_distributionNamedl NOT_ATTRIBUTE_IS_MISSING ""
    PASSED -> XMLTemplater [input 8]
    PASSED -> DuplicateRemover_2
    PASSED -> DuplicateRemover_4
    PASSED -> DuplicateRemover_3
distributionFunctiodl: Tester
    TEST_MODE = Automatic
    TEST_DESCRIPTION = ""
    BOOL_OP = AND
    TEST_CLAUSE:
      TEST Distributiononline_distributionFunctiodl NOT_ATTRIBUTE_VALUE_NULL ""
      TEST Distributiononline_distributionFunctiodl NOT_ATTRIBUTE_IS_EMPTY ""
      TEST Distributiononline_distributionFunctiodl NOT_ATTRIBUTE_IS_MISSING ""
    PASSED -> XMLTemplater [input 9]
    PASSED -> DuplicateRemover_2
    PASSED -> DuplicateRemover_4
    PASSED -> DuplicateRemover_3
DuplicateRemover_2
    KEYATTR = Distributiononline__count
    UNIQUE -> XMLTemplater [input 1]
DuplicateRemover_3
    KEYATTR = Distributiononline__count
    UNIQUE -> XMLTemplater [input 3]
DuplicateRemover_4
    KEYATTR = Distributiononline__count
    UNIQUE -> XMLTemplater [input 10]
XMLTemplater
    GROUP_BY = Distributiononline__count
    NAMEFORMAT_QUERY_EXPR:
      <gmd:name>
      		<gco:CharacterString>{fme:get-attribute("Distributiononline_nameformat1")}</gco:CharacterString>
      </gmd:name>
    ROOT_QUERY_EXPR:
          <?xml version="1.0" encoding="UTF-8"?>
      <rw:MD_Metadata xmlns:rw="http://metawal.wallonie.be/schemas/3.0" xmlns:gmd="http://www.isotc211.org/2005/gmd" xmlns:gts="http://www.isotc211.org/2005/gts" xmlns:gco="http://www.isotc211.org/2005/gco" xmlns:gml="http://www.opengis.net/gml" xmlns:geonet="http://www.fao.org/geonetwork" xmlns:xsi="http://www.w3.org/2001/XMLSchema-instance" gco:isoType="gmd:MD_Metadata" xsi:schemaLocation="http://metawal.wallonie.be/schemas/3.0 file:///H:/gimb14/c/c130606/data/schemas/rwschema.xsd">
      {fme:process-features("ORDERINGINSTRUCTIONS")}

      {fme:process-features("DISTRUBUTIONFORMAT_INFO")}

      {fme:process-features("TRANSFEROPTION")}


      </rw:MD_Metadata>
    PROTOCOL_QUERY_EXPR:
      <gmd:protocol>
      			<gco:CharacterString>{fme:get-attribute("Distributiononline_distributionProtocoldl")}</gco:CharacterString>
      </gmd:protocol>
    DESCRIPTION_QUERY_EXPR:
      <gmd:description>
      		<gco:CharacterString>{fme:get-attribute("Distributiononline_distributionDescriptiodl")}</gco:CharacterString>
      </gmd:description>
    VISIBLE_QUERY_VALIDATE = Yes
    TRANSFEROPTION_QUERY_EXPR:
      		<gmd:distributorTransferOptions>
      				<gmd:MD_DigitalTransferOptions>
      			{fme:process-features("TRANSFERSIZE")}
                {fme:process-features("ONLINERESSOURCE")}
      					</gmd:MD_DigitalTransferOptions>
      			</gmd:distributorTransferOptions>
    ORDERINGINSTRUCTIONS_QUERY_EXPR:
      <gmd:distributionOrderProcess>
      						<gmd:MD_StandardOrderProcess>
      							<gmd:orderingInstructions>
      								<gco:CharacterString>{fme:get-attribute("Distributiononline_orderingInstructions1")}</gco:CharacterString>
      							</gmd:orderingInstructions>
      						</gmd:MD_StandardOrderProcess>
      </gmd:distributionOrderProcess>
    OUTPUT_XML_HEADER = Yes
    LINKAGE_QUERY_EXPR:
      <gmd:linkage>
      			<gmd:URL>{fme:get-attribute("Distributiononline_dirstributionURLdl")}</gmd:URL>
      </gmd:linkage>
    DISTRUBUTIONFORMAT_INFO_QUERY_EXPR:
      			<gmd:distributorFormat>
      				<gmd:MD_Format>
      				{fme:process-features("NAMEFORMAT")}
      				{fme:process-features("VERSIONFORMAT")}
      				</gmd:MD_Format>
      			</gmd:distributorFormat>
    FUNCTION_QUERY_EXPR:
      	<gmd:function>
      			<gmd:CI_OnLineFunctionCode codeList="http://standards.iso.org/ittf/PubliclyAvailableStandards/ISO_19139_Schemas/resources/Codelist/ML_gmxCodelists.xml#CI_OnLineFunctionCode" codeListValue="{fme:get-attribute("Distributiononline_distributionFunctiodl")}"/>
      	</gmd:function>
    ONLINERESSOURCE_QUERY_EXPR:
      <gmd:onLine>
      	<gmd:CI_OnlineResource>
      		{fme:process-features("LINKAGE")}
      		{fme:process-features("PROTOCOL")}
              {fme:process-features("NAME")}
              {fme:process-features("DESCRIPTION")}
              {fme:process-features("FUNCTION")}
      	</gmd:CI_OnlineResource>
      </gmd:onLine>
    NAME_QUERY_EXPR:
      <gmd:name>
      		<gco:CharacterString>{fme:get-attribute("Distributiononline_distributionNamedl")}</gco:CharacterString>
      </gmd:name>
    RESULT_ATTRIBUTE = _result
    TRANSFERSIZE_QUERY_EXPR:
      	<gmd:transferSize>
      				<gco:Real>{fme:get-attribute("Distribution_transfersize")}</gco:Real>
      	</gmd:transferSize>
    CONSECUTIVE_GROUPS = No
    VERSIONFORMAT_QUERY_EXPR:
      <gmd:version>
      		<gco:CharacterString>{fme:get-attribute("Distributiononline_versionFormat1")}</gco:CharacterString>
      </gmd:version>
    -> Tester_39_Passed (output)
Tester_39_Passed (output)

FME custom transformer Distributor

Parameters:
- CONTACTSUPP__COUNT = @Value(Contactsupp__count)   # Contactsupp Count
- CONTACTSUPP_ROLE = @Value(Contactsupp_Role)   # Contactsupp Role
- CONTACTSUPP_ORGANISATIONNAME = @Value(Contactsupp_organisationName)   # Contactsupp Organisationname
- CONTACTSUPP_ELECTRONICMAILADDRESS = @Value(Contactsupp_electronicMailAddress)   # Contactsupp Electronicmailaddress
- CONTACTSUPP_INDIVIDUALNAME = @Value(Contactsupp_individualName)   # Contactsupp Individualname
- CONTACTSUPP_POSITIONNAME = @Value(Contactsupp_positionName)   # Contactsupp Positionname
- CONTACTSUPP_VOICE = @Value(Contactsupp_voice)   # Contactsupp Voice
- CONTACTSUPP_DELIVERYPOINT = @Value(Contactsupp_deliveryPoint)   # Contactsupp Deliverypoint
- CONTACTSUPP_CITY = @Value(Contactsupp_city)   # Contactsupp City
- CONTACTSUPP_POSTALCODE = @Value(Contactsupp_postalCode)   # Contactsupp Postalcode
- CONTACTSUPP_COUNTRY = @Value(Contactsupp_country)   # Contactsupp Country
- CONTACTSUPP_LINKAGE = @Value(Contactsupp_linkage)   # Contactsupp Linkage
- CONTACTSUPP_PROTOCOLE = @Value(Contactsupp_protocole)   # Contactsupp Protocole
- CONTACTSUPP_NAME = @Value(Contactsupp_name)   # Contactsupp Name
- CONTACTSUPP_DESCRIPTION = @Value(Contactsupp_description)   # Contactsupp Description
- CONTACTSUPP_FUNCTION = @Value(Contactsupp_function)   # Contactsupp Function
- CONTACTSUPP_ROLE_TYPE = @Value(Contactsupp_Role_type)   # Contactsupp Role Type
- CONTACTSUPP__ELEMENT_INDEX = @Value(Contactsupp__element_index)   # Contactsupp Element Index
- DISTRIBUTIONONLINE_DISTRIBUTEUR = @Value(Distributiononline_Distributeur)   # Distributiononline Distributeur

Distributeur (input)
    -> Tester
Tester
    TEST_MODE = Automatic
    TEST_DESCRIPTION = ""
    BOOL_OP = AND
    TEST_CLAUSE:
      TEST Distributiononline_Distributeur NOT_ATTRIBUTE_VALUE_NULL ""
      TEST Distributiononline_Distributeur NOT_ATTRIBUTE_IS_EMPTY ""
      TEST Distributiononline_Distributeur NOT_ATTRIBUTE_IS_MISSING ""
    PASSED -> linkage_2
    PASSED -> name_2
    PASSED -> deliveryPoint_2
    PASSED -> electronicmailAddress_2
    PASSED -> function_2
    PASSED -> organisationname_2
    PASSED -> role_2
    PASSED -> voice_2
    PASSED -> description_2
    PASSED -> positionName_2
    PASSED -> city_2
    PASSED -> country_2
    PASSED -> postalcode_2
    PASSED -> individualname_2
    PASSED -> protocole_2
role_2: Tester
    TEST_MODE = Automatic
    TEST_DESCRIPTION = ""
    BOOL_OP = AND
    TEST_CLAUSE:
      TEST Contactsupp_Role NOT_ATTRIBUTE_VALUE_NULL ""
      TEST Contactsupp_Role NOT_ATTRIBUTE_IS_EMPTY ""
      TEST Contactsupp_Role NOT_ATTRIBUTE_IS_MISSING ""
    PASSED -> XMLTemplater_2 [input 4]
    PASSED -> DuplicateRemover_2
organisationname_2: Tester
    TEST_MODE = Automatic
    TEST_DESCRIPTION = ""
    BOOL_OP = AND
    TEST_CLAUSE:
      TEST Contactsupp_organisationName NOT_ATTRIBUTE_VALUE_NULL ""
      TEST Contactsupp_organisationName NOT_ATTRIBUTE_IS_EMPTY ""
      TEST Contactsupp_organisationName NOT_ATTRIBUTE_IS_MISSING ""
    PASSED -> XMLTemplater_2 [input 5]
    PASSED -> DuplicateRemover_2
electronicmailAddress_2: Tester
    TEST_MODE = Automatic
    TEST_DESCRIPTION = ""
    BOOL_OP = AND
    TEST_CLAUSE:
      TEST Contactsupp_electronicMailAddress NOT_ATTRIBUTE_VALUE_NULL ""
      TEST Contactsupp_electronicMailAddress NOT_ATTRIBUTE_IS_EMPTY ""
      TEST Contactsupp_electronicMailAddress NOT_ATTRIBUTE_IS_MISSING ""
    PASSED -> XMLTemplater_2 [input 8]
    PASSED -> DuplicateRemover_2
individualname_2: Tester
    TEST_MODE = Automatic
    TEST_DESCRIPTION = ""
    BOOL_OP = AND
    TEST_CLAUSE:
      TEST Contactsupp_individualName NOT_ATTRIBUTE_VALUE_NULL ""
      TEST Contactsupp_individualName NOT_ATTRIBUTE_IS_EMPTY ""
      TEST Contactsupp_individualName NOT_ATTRIBUTE_IS_MISSING ""
    PASSED -> DuplicateRemover_2
    PASSED -> XMLTemplater_2 [input 2]
positionName_2: Tester
    TEST_MODE = Automatic
    TEST_DESCRIPTION = ""
    BOOL_OP = AND
    TEST_CLAUSE:
      TEST Contactsupp_positionName NOT_ATTRIBUTE_VALUE_NULL ""
      TEST Contactsupp_positionName NOT_ATTRIBUTE_IS_EMPTY ""
      TEST Contactsupp_positionName NOT_ATTRIBUTE_IS_MISSING ""
    PASSED -> DuplicateRemover_2
    PASSED -> XMLTemplater_2 [input 6]
voice_2: Tester
    TEST_MODE = Automatic
    TEST_DESCRIPTION = ""
    BOOL_OP = AND
    TEST_CLAUSE:
      TEST Contactsupp_voice NOT_ATTRIBUTE_VALUE_NULL ""
      TEST Contactsupp_voice NOT_ATTRIBUTE_IS_EMPTY ""
      TEST Contactsupp_voice NOT_ATTRIBUTE_IS_MISSING ""
    PASSED -> DuplicateRemover_2
    PASSED -> XMLTemplater_2 [input 7]
deliveryPoint_2: Tester
    TEST_MODE = Automatic
    TEST_DESCRIPTION = ""
    BOOL_OP = AND
    TEST_CLAUSE:
      TEST Contactsupp_deliveryPoint NOT_ATTRIBUTE_VALUE_NULL ""
      TEST Contactsupp_deliveryPoint NOT_ATTRIBUTE_IS_EMPTY ""
      TEST Contactsupp_deliveryPoint NOT_ATTRIBUTE_IS_MISSING ""
    PASSED -> DuplicateRemover_2
    PASSED -> XMLTemplater_2 [input 9]
city_2: Tester
    TEST_MODE = Automatic
    TEST_DESCRIPTION = ""
    BOOL_OP = AND
    TEST_CLAUSE:
      TEST Contactsupp_city NOT_ATTRIBUTE_VALUE_NULL ""
      TEST Contactsupp_city NOT_ATTRIBUTE_IS_EMPTY ""
      TEST Contactsupp_city NOT_ATTRIBUTE_IS_MISSING ""
    PASSED -> DuplicateRemover_2
    PASSED -> XMLTemplater_2 [input 10]
postalcode_2: Tester
    TEST_MODE = Automatic
    TEST_DESCRIPTION = ""
    BOOL_OP = AND
    TEST_CLAUSE:
      TEST Contactsupp_postalCode NOT_ATTRIBUTE_VALUE_NULL ""
      TEST Contactsupp_postalCode NOT_ATTRIBUTE_IS_EMPTY ""
      TEST Contactsupp_postalCode NOT_ATTRIBUTE_IS_MISSING ""
    PASSED -> DuplicateRemover_2
    PASSED -> DuplicateRemover_3
    PASSED -> XMLTemplater_2 [input 11]
country_2: Tester
    TEST_MODE = Automatic
    TEST_DESCRIPTION = ""
    BOOL_OP = AND
    TEST_CLAUSE:
      TEST Contactsupp_country NOT_ATTRIBUTE_VALUE_NULL ""
      TEST Contactsupp_country NOT_ATTRIBUTE_IS_EMPTY ""
      TEST Contactsupp_country NOT_ATTRIBUTE_IS_MISSING ""
    PASSED -> DuplicateRemover_2
    PASSED -> XMLTemplater_2 [input 12]
linkage_2: Tester
    TEST_MODE = Automatic
    TEST_DESCRIPTION = ""
    BOOL_OP = AND
    TEST_CLAUSE:
      TEST Contactsupp_linkage NOT_ATTRIBUTE_VALUE_NULL ""
      TEST Contactsupp_linkage NOT_ATTRIBUTE_IS_EMPTY ""
      TEST Contactsupp_linkage NOT_ATTRIBUTE_IS_MISSING ""
    PASSED -> DuplicateRemover_2
    PASSED -> DuplicateRemover_3
    PASSED -> XMLTemplater_2 [input 14]
protocole_2: Tester
    TEST_MODE = Automatic
    TEST_DESCRIPTION = ""
    BOOL_OP = AND
    TEST_CLAUSE:
      TEST Contactsupp_protocole NOT_ATTRIBUTE_VALUE_NULL ""
      TEST Contactsupp_protocole NOT_ATTRIBUTE_IS_EMPTY ""
      TEST Contactsupp_protocole NOT_ATTRIBUTE_IS_MISSING ""
    PASSED -> DuplicateRemover_2
    PASSED -> DuplicateRemover_3
    PASSED -> XMLTemplater_2 [input 15]
name_2: Tester
    TEST_MODE = Automatic
    TEST_DESCRIPTION = ""
    BOOL_OP = AND
    TEST_CLAUSE:
      TEST Contactsupp_name NOT_ATTRIBUTE_VALUE_NULL ""
      TEST Contactsupp_name NOT_ATTRIBUTE_IS_EMPTY ""
      TEST Contactsupp_name NOT_ATTRIBUTE_IS_MISSING ""
    PASSED -> DuplicateRemover_2
    PASSED -> DuplicateRemover_3
    PASSED -> XMLTemplater_2 [input 16]
description_2: Tester
    TEST_MODE = Automatic
    TEST_DESCRIPTION = ""
    BOOL_OP = AND
    TEST_CLAUSE:
      TEST Contactsupp_description NOT_ATTRIBUTE_VALUE_NULL ""
      TEST Contactsupp_description NOT_ATTRIBUTE_IS_EMPTY ""
      TEST Contactsupp_description NOT_ATTRIBUTE_IS_MISSING ""
    PASSED -> DuplicateRemover_2
    PASSED -> DuplicateRemover_3
    PASSED -> XMLTemplater_2 [input 17]
function_2: Tester
    TEST_MODE = Automatic
    TEST_DESCRIPTION = ""
    BOOL_OP = AND
    TEST_CLAUSE:
      TEST Contactsupp_function NOT_ATTRIBUTE_VALUE_NULL ""
      TEST Contactsupp_function NOT_ATTRIBUTE_IS_EMPTY ""
      TEST Contactsupp_function NOT_ATTRIBUTE_IS_MISSING ""
    PASSED -> DuplicateRemover_2
    PASSED -> DuplicateRemover_3
    PASSED -> XMLTemplater_2 [input 18]
DuplicateRemover_2
    KEYATTR = Contactsupp__count
    UNIQUE -> DuplicateRemover_4
DuplicateRemover_3
    KEYATTR = Contactsupp__count
    UNIQUE -> XMLTemplater_2 [input 13]
    UNIQUE -> DuplicateRemover_4
DuplicateRemover_4
    KEYATTR = Contactsupp__count
    UNIQUE -> XMLTemplater_2 [input 1]
    UNIQUE -> XMLTemplater_2 [input 3]
XMLTemplater_2
    GROUP_BY = Contactsupp__count
    POSTALCODE_QUERY_EXPR:
      <gmd:postalCode>
      			<gco:CharacterString>{fme:get-attribute("Contactsupp_postalCode")}</gco:CharacterString>
      </gmd:postalCode>
    ROOT_QUERY_EXPR:
          <?xml version="1.0" encoding="UTF-8"?>
      <rw:MD_Metadata xmlns:rw="http://metawal.wallonie.be/schemas/3.0" xmlns:gmd="http://www.isotc211.org/2005/gmd" xmlns:gts="http://www.isotc211.org/2005/gts" xmlns:gco="http://www.isotc211.org/2005/gco" xmlns:gml="http://www.opengis.net/gml" xmlns:geonet="http://www.fao.org/geonetwork" xmlns:xsi="http://www.w3.org/2001/XMLSchema-instance" gco:isoType="gmd:MD_Metadata" xsi:schemaLocation="http://metawal.wallonie.be/schemas/3.0 file:///H:/gimb14/c/c130606/data/schemas/rwschema.xsd">

      {fme:process-features("ONLINE")}

      </rw:MD_Metadata>
    POSITION_NAME_QUERY_EXPR:
      <gmd:positionName>
      		<gco:CharacterString>{fme:get-attribute("Contactsupp_positionName")}</gco:CharacterString>
      </gmd:positionName>
    PROTOCOL_QUERY_EXPR:
      <gmd:protocol>
      		<gco:CharacterString>{fme:get-attribute("Contactsupp_protocole")}</gco:CharacterString>
      </gmd:protocol>
    DESCRIPTION_QUERY_EXPR:
      	<gmd:description>
      				<gco:CharacterString>{fme:get-attribute("Contactsupp_description")}</gco:CharacterString>
      	</gmd:description>
    VISIBLE_QUERY_VALIDATE = Yes
    ADRESSE_MAIL_QUERY_EXPR:
      <gmd:electronicMailAddress>
      			<gco:CharacterString>{fme:get-attribute("Contactsupp_electronicMailAddress")}</gco:CharacterString>
      </gmd:electronicMailAddress>
    DELIVERY_POINT_QUERY_EXPR:
      	<gmd:deliveryPoint>
      		<gco:CharacterString>{fme:get-attribute("Contactsupp_deliveryPoint")}</gco:CharacterString>
      	</gmd:deliveryPoint>
    INDIVIDUAL_NAME_QUERY_EXPR:
      <gmd:individualName>
      		<gco:CharacterString>{fme:get-attribute("Contactsupp_individualName")}</gco:CharacterString>
      </gmd:individualName>
    COUNTRY_QUERY_EXPR:
      		<gmd:country>
      			<gco:CharacterString>{fme:get-attribute("Contactsupp_country")}</gco:CharacterString>
      		</gmd:country>
    ONLINE_RESSOURCE_QUERY_EXPR:
      	<gmd:onlineResource>
      				<gmd:CI_OnlineResource>
      						{fme:process-features("LINKAGE")}
      						{fme:process-features("PROTOCOL")}
      						{fme:process-features("NAME")}
      						{fme:process-features("DESCRIPTION")}
      						{fme:process-features("FUNCTION")}
      				</gmd:CI_OnlineResource>
          </gmd:onlineResource>
    VOICE_QUERY_EXPR:
      <gmd:phone>
      			<gmd:CI_Telephone>
      					<gmd:voice>
      							<gco:CharacterString>{fme:get-attribute("Contactsupp_voice")}</gco:CharacterString>
      					</gmd:voice>
      			</gmd:CI_Telephone>
      </gmd:phone>
    OUTPUT_XML_HEADER = Yes
    LINKAGE_QUERY_EXPR:
      	<gmd:linkage>
      				<gmd:URL>{fme:get-attribute("Contactsupp_linkage")}</gmd:URL>
      	</gmd:linkage>
    ORGANISATION_NAME_QUERY_EXPR:
       <gmd:organisationName>
      			<gco:CharacterString>{fme:get-attribute("Contactsupp_organisationName")}</gco:CharacterString>
      </gmd:organisationName>
    ONLINE_QUERY_EXPR:
      					<gmd:distributorContact>
      						<gmd:CI_ResponsibleParty>
      							{fme:process-features("ORGANISATION_NAME")}
      							<gmd:contactInfo>
      								<gmd:CI_Contact>
      									<gmd:address>
      										<gmd:CI_Address>
      										{fme:process-features("ADRESSE_MAIL")}
      										</gmd:CI_Address>
      									</gmd:address>
      									{fme:process-features("ONLINE_RESSOURCE")}
      								</gmd:CI_Contact>
      							</gmd:contactInfo>
      							<gmd:role>
      								<gmd:CI_RoleCode codeList="http://standards.iso.org/ittf/PubliclyAvailableStandards/ISO_19139_Schemas/resources/Codelist/ML_gmxCodelists.xml#CI_RoleCode" codeListValue="distributor"/>
      							</gmd:role>
      						</gmd:CI_ResponsibleParty>
      					</gmd:distributorContact>
    FUNCTION_QUERY_EXPR:
      	<gmd:function>
      			<gmd:CI_OnLineFunctionCode codeList="http://standards.iso.org/ittf/PubliclyAvailableStandards/ISO_19139_Schemas/resources/Codelist/ML_gmxCodelists.xml#CI_OnLineFunctionCode" codeListValue="{fme:get-attribute("Contactsupp_function")}"/>
      	</gmd:function>
    NAME_QUERY_EXPR:
      <gmd:name>
      			<gco:CharacterString>{fme:get-attribute("Contactsupp_name")}</gco:CharacterString>
      </gmd:name>
    ROLE_QUERY_EXPR:
      <gmd:role>
      		<gmd:CI_RoleCode codeList="http://standards.iso.org/ittf/PubliclyAvailableStandards/ISO_19139_Schemas/resources/Codelist/ML_gmxCodelists.xml#CI_RoleCode" codeListValue="{fme:get-attribute("Contactsupp_Role")}"/>
      </gmd:role>
    RESULT_ATTRIBUTE = _result
    CONSECUTIVE_GROUPS = No
    CITY_QUERY_EXPR:
      <gmd:city>
      			<gco:CharacterString>{fme:get-attribute("Contactsupp_city")}</gco:CharacterString>
      </gmd:city>
    -> modif_texte_8_StringReplacer_2_Output_2 (output)
modif_texte_8_StringReplacer_2_Output_2 (output)

FME custom transformer INFO_SUPP

Parameters:
- ID = @Value(ID)   # Id
- PARENTIDENTIFIER = @Value(parentIdentifier)   # Parentidentifier
- HIERARCHYLEVEL = @Value(hierarchyLevel)   # Hierarchylevel
- HIERARCHYLEVELNAME = @Value(hierarchyLevelName)   # Hierarchylevelname
- TITLE = @Value(title)   # Title
- ALTERNATETITLE = @Value(alternateTitle)   # Alternatetitle
- ACRONYM = @Value(acronym)   # Acronym
- VERSIONYEAR = @Value(versionYear)   # Versionyear
- AOI = @Value(AOI)   # Aoi
- CREATION_DATE = @Value(creation_date)   # Creation Date
- PUBLICATION_DATE = @Value(publication_date)   # Publication Date
- REVISION_DATE = @Value(revision_date)   # Revision Date
- LOCALCODE = @Value(localCode)   # Localcode
- ABSTRACT = @Value(abstract)   # Abstract
- ABSTRACT_BODY = @Value(abstract_body)   # Abstract Body
- STATUS = @Value(status)   # Status
- MAINTENANCEANDUPDATEFREQUENCY = @Value(maintenanceAndUpdateFrequency)   # Maintenanceandupdatefrequency
- MAINTENANCENOTE = @Value(maintenanceNote)   # Maintenancenote
- FILENAME = @Value(fileName)   # Filename
- FILEDESCRIPTION = @Value(fileDescription)   # Filedescription
- FILETYPE = @Value(fileType)   # Filetype
- SPATIALREPRESENTATIONTYPE = @Value(spatialRepresentationType)   # Spatialrepresentationtype
- BEGINPOSITION = @Value(beginPosition)   # Beginposition
- ENDPOSITION = @Value(endPosition)   # Endposition
- STATEMENTLINEAGE = @Value(statementLineage)   # Statementlineage
- INSPIRECONFORMITY = @Value(INSPIREConformity)   # Inspireconformity
- NAMEOFMEASURE = @Value(nameOfMeasure)   # Nameofmeasure
- CONSISTENCYTITLE = @Value(consistencyTitle)   # Consistencytitle
- CONSISTENCYALTERNATETITLE = @Value(consistencyAlternateTitle)   # Consistencyalternatetitle
- CONSISTENCYCODE = @Value(consistencyCode)   # Consistencycode
- CONSISTENCYDESCRIPTION = @Value(consistencyDescription)   # Consistencydescription
- EVALUATIONMETHODTYPE = @Value(evaluationMethodType)   # Evaluationmethodtype
- DATETIME = @Value(dateTime)   # Datetime
- CONFORMANCETITLE = @Value(conformanceTitle)   # Conformancetitle
- CONFORMANCEALTERNATETITLE = @Value(conformanceAlternateTitle)   # Conformancealternatetitle
- CONFORMANCEDATE = @Value(conformanceDate)   # Conformancedate
- CONFORMANCEDATETYPE = @Value(conformanceDateType)   # Conformancedatetype
- CONFORMANCEEXPLANATION = @Value(conformanceExplanation)   # Conformanceexplanation
- CONFORMANCEPASS = @Value(conformancePass)   # Conformancepass
- QUANTITATIVERESULTVALUE = @Value(quantitativeResultValue)   # Quantitativeresultvalue
- CHARACTERSET = @Value(characterSet)   # Characterset
- METADATASTANDARDNAME = @Value(metadataStandardName)   # Metadatastandardname
- METADATASTANDARDVERSION = @Value(metadataStandardVersion)   # Metadatastandardversion
- CODESPACE = @Value(CodeSpace)   # Codespace
- METADATA_LANG = @Value(metadata_lang)   # Metadata Lang
- REFERENCESYSTEMCODE = @Value(referenceSystemCode)   # Referencesystemcode
- CODESPACEREFERENCESYSTEM = @Value(CodeSpaceReferenceSystem)   # Codespacereferencesystem
- VERSION = @Value(Version)   # Version
- LANGUAGE = @Value(language)   # Language
- CHARACTERSETRESSOURCE = @Value(characterSetRessource)   # Charactersetressource
- SPATIALDESCRIPTION = @Value(spatialDescription)   # Spatialdescription
- WESTBOUNDLONGITUDE = @Value(westBoundLongitude)   # Westboundlongitude
- EASTBOUNDLONGITUDE = @Value(eastBoundLongitude)   # Eastboundlongitude
- SOUTHBOUNDLATITUDE = @Value(southBoundLatitude)   # Southboundlatitude
- NORTHBOUNDLATITUDE = @Value(northBoundLatitude)   # Northboundlatitude
- MINIMUMVALUE = @Value(minimumValue)   # Minimumvalue
- MAXIMUMVALUE = @Value(maximumValue)   # Maximumvalue
- LEVEL = @Value(level)   # Level
- CLASSIFICATION = @Value(classification)   # Classification
- USELIMITATION1 = @Value(useLimitation1)   # Uselimitation1
- USELIMITATION2 = @Value(useLimitation2)   # Uselimitation2
- ACCESSCONSTRAINTS = @Value(accessConstraints)   # Accessconstraints
- USECONSTRAINTS = @Value(useConstraints)   # Useconstraints
- OTHERCONSTRAINTS1 = @Value(otherConstraints1)   # Otherconstraints1
- OTHERCONSTRAINTS2 = @Value(otherConstraints2)   # Otherconstraints2
- USELIMITATION3 = @Value(useLimitation3)   # Uselimitation3
- USELIMITATION4 = @Value(useLimitation4)   # Uselimitation4

Input_2 (input)
    -> filename
    -> filedescription
    -> filetype
filename: Tester
    TEST_MODE = Automatic
    TEST_DESCRIPTION = ""
    BOOL_OP = AND
    TEST_CLAUSE:
      TEST fileName NOT_ATTRIBUTE_VALUE_NULL ""
      TEST fileName NOT_ATTRIBUTE_IS_EMPTY ""
      TEST fileName NOT_ATTRIBUTE_IS_MISSING ""
    PASSED -> XMLTemplater33 [input 2]
    PASSED -> DuplicateRemover
filedescription: Tester
    TEST_MODE = Automatic
    TEST_DESCRIPTION = ""
    BOOL_OP = AND
    TEST_CLAUSE:
      TEST fileDescription NOT_ATTRIBUTE_VALUE_NULL ""
      TEST fileDescription NOT_ATTRIBUTE_IS_EMPTY ""
      TEST fileDescription NOT_ATTRIBUTE_IS_MISSING ""
    PASSED -> XMLTemplater33 [input 3]
    PASSED -> DuplicateRemover
filetype: Tester
    TEST_MODE = Automatic
    TEST_DESCRIPTION = ""
    BOOL_OP = AND
    TEST_CLAUSE:
      TEST fileType NOT_ATTRIBUTE_VALUE_NULL ""
      TEST fileType NOT_ATTRIBUTE_IS_EMPTY ""
      TEST fileType NOT_ATTRIBUTE_IS_MISSING ""
    PASSED -> XMLTemplater33 [input 4]
    PASSED -> DuplicateRemover
DuplicateRemover
    KEYATTR = ID
    UNIQUE -> XMLTemplater33 [input 1]
XMLTemplater33
    RESULT_ATTRIBUTE = _result
    FILENAME_QUERY_EXPR:
      <gmd:fileName>
      			<gco:CharacterString>{fme:get-attribute("fileName")}</gco:CharacterString>
      </gmd:fileName>
    ROOT_QUERY_EXPR:
      <?xml version="1.0" encoding="UTF-8"?>
      <rw:MD_Metadata xmlns:rw="http://metawal.wallonie.be/schemas/3.0" xmlns:gmd="http://www.isotc211.org/2005/gmd" xmlns:gts="http://www.isotc211.org/2005/gts" xmlns:gco="http://www.isotc211.org/2005/gco" xmlns:gml="http://www.opengis.net/gml" xmlns:geonet="http://www.fao.org/geonetwork" xmlns:xsi="http://www.w3.org/2001/XMLSchema-instance" gco:isoType="gmd:MD_Metadata" xsi:schemaLocation="http://metawal.wallonie.be/schemas/3.0 file:///H:/gimb14/c/c130606/data/schemas/rwschema.xsd">
      <gmd:graphicOverview xmlns:srv="http://www.isotc211.org/2005/srv">
      		<gmd:MD_BrowseGraphic>
      {fme:process-features("FILENAME")}
      {fme:process-features("FILEDESCRIPTION")}
      {fme:process-features("FILETYPE")}
          </gmd:MD_BrowseGraphic>
      			</gmd:graphicOverview>

      </rw:MD_Metadata>
    FILEDESCRIPTION_QUERY_EXPR:
      <gmd:fileDescription>
      			<gco:CharacterString>{fme:get-attribute("fileDescription")}</gco:CharacterString>
      </gmd:fileDescription>
    FILETYPE_QUERY_EXPR:
      <gmd:fileType>
      		<gco:CharacterString>{fme:get-attribute("fileType")}</gco:CharacterString>
      </gmd:fileType>
    VISIBLE_QUERY_VALIDATE = Yes
    OUTPUT_XML_HEADER = Yes
    -> Output_2 (output)
Output_2 (output)

FME custom transformer modif_texte

Parameters:
- _RESULT = @Value(_result)   # Result

StringReplacer_Input (input)
    -> StringReplacer
StringReplacer
    SRC_ATTRS = _result
    REGEXP = no
    CASE = no
    NO_MATCH = _FME_NO_OP_
    FIND_TEXT = <?xml version="1.0" encoding="UTF-8"?>
    -> StringReplacer_3
StringReplacer_3
    SRC_ATTRS = _result
    REGEXP = no
    CASE = no
    NO_MATCH = _FME_NO_OP_
    FIND_TEXT = <rw:MD_Metadata xmlns:rw="http://metawal.wallonie.be/schemas/3.0" xmlns:gmd="http://www.isotc211.org/2005/gmd" xmlns:gts="http://www.isotc211.org/2005/gts" xmlns:gco="http://www.isotc211.org/2005/gco" xmlns:gml="http://www.opengis.net/gml" xmlns:geonet="http://www.fao.org/geonetwork" xmlns:xsi="http://www.w3.org/2001/XMLSchema-instance" gco:isoType="gmd:MD_Metadata" xsi:schemaLocation="http://metawal.wallonie.be/schemas/3.0 file:///H:/gimb14/c/c130606/data/schemas/rwschema.xsd">
    -> StringReplacer_2
StringReplacer_2
    SRC_ATTRS = _result
    REGEXP = no
    CASE = no
    NO_MATCH = _FME_NO_OP_
    FIND_TEXT = </rw:MD_Metadata>
    -> StringReplacer_2_Output (output)
StringReplacer_2_Output (output)

FME custom transformer CONTACTS

Parameters:
- CONTACTSUPP__COUNT = @Value(Contactsupp__count)   # Contactsupp Count
- CONTACTSUPP_ROLE = @Value(Contactsupp_Role)   # Contactsupp Role
- CONTACTSUPP_ORGANISATIONNAME = @Value(Contactsupp_organisationName)   # Contactsupp Organisationname
- CONTACTSUPP_ELECTRONICMAILADDRESS = @Value(Contactsupp_electronicMailAddress)   # Contactsupp Electronicmailaddress
- CONTACTSUPP_INDIVIDUALNAME = @Value(Contactsupp_individualName)   # Contactsupp Individualname
- CONTACTSUPP_POSITIONNAME = @Value(Contactsupp_positionName)   # Contactsupp Positionname
- CONTACTSUPP_VOICE = @Value(Contactsupp_voice)   # Contactsupp Voice
- CONTACTSUPP_DELIVERYPOINT = @Value(Contactsupp_deliveryPoint)   # Contactsupp Deliverypoint
- CONTACTSUPP_CITY = @Value(Contactsupp_city)   # Contactsupp City
- CONTACTSUPP_POSTALCODE = @Value(Contactsupp_postalCode)   # Contactsupp Postalcode
- CONTACTSUPP_COUNTRY = @Value(Contactsupp_country)   # Contactsupp Country
- CONTACTSUPP_LINKAGE = @Value(Contactsupp_linkage)   # Contactsupp Linkage
- CONTACTSUPP_PROTOCOLE = @Value(Contactsupp_protocole)   # Contactsupp Protocole
- CONTACTSUPP_NAME = @Value(Contactsupp_name)   # Contactsupp Name
- CONTACTSUPP_DESCRIPTION = @Value(Contactsupp_description)   # Contactsupp Description
- CONTACTSUPP_FUNCTION = @Value(Contactsupp_function)   # Contactsupp Function
- CONTACTSUPP_ROLE_TYPE = @Value(Contactsupp_Role_type)   # Contactsupp Role Type
- CONTACTSUPP__ELEMENT_INDEX = @Value(Contactsupp__element_index)   # Contactsupp Element Index

INPUT (input)
    -> role
    -> organisationname
    -> electronicmailAddress
    -> individualname
    -> positionName
    -> voice
    -> deliveryPoint
    -> city
    -> postalcode
    -> country
    -> linkage
    -> protocole
    -> name
    -> description
    -> function
role: Tester
    TEST_MODE = Automatic
    TEST_DESCRIPTION = ""
    BOOL_OP = AND
    TEST_CLAUSE:
      TEST Contactsupp_Role NOT_ATTRIBUTE_VALUE_NULL ""
      TEST Contactsupp_Role NOT_ATTRIBUTE_IS_EMPTY ""
      TEST Contactsupp_Role NOT_ATTRIBUTE_IS_MISSING ""
    PASSED -> XMLTemplater_10 [input 3]
    PASSED -> DuplicateRemover_16
organisationname: Tester
    TEST_MODE = Automatic
    TEST_DESCRIPTION = ""
    BOOL_OP = AND
    TEST_CLAUSE:
      TEST Contactsupp_organisationName NOT_ATTRIBUTE_VALUE_NULL ""
      TEST Contactsupp_organisationName NOT_ATTRIBUTE_IS_EMPTY ""
      TEST Contactsupp_organisationName NOT_ATTRIBUTE_IS_MISSING ""
    PASSED -> XMLTemplater_10 [input 4]
    PASSED -> DuplicateRemover_16
electronicmailAddress: Tester
    TEST_MODE = Automatic
    TEST_DESCRIPTION = ""
    BOOL_OP = AND
    TEST_CLAUSE:
      TEST Contactsupp_electronicMailAddress NOT_ATTRIBUTE_VALUE_NULL ""
      TEST Contactsupp_electronicMailAddress NOT_ATTRIBUTE_IS_EMPTY ""
      TEST Contactsupp_electronicMailAddress NOT_ATTRIBUTE_IS_MISSING ""
    PASSED -> XMLTemplater_10 [input 8]
    PASSED -> DuplicateRemover_16
individualname: Tester
    TEST_MODE = Automatic
    TEST_DESCRIPTION = ""
    BOOL_OP = AND
    TEST_CLAUSE:
      TEST Contactsupp_individualName NOT_ATTRIBUTE_VALUE_NULL ""
      TEST Contactsupp_individualName NOT_ATTRIBUTE_IS_EMPTY ""
      TEST Contactsupp_individualName NOT_ATTRIBUTE_IS_MISSING ""
    PASSED -> DuplicateRemover_16
    PASSED -> XMLTemplater_10 [input 2]
positionName: Tester
    TEST_MODE = Automatic
    TEST_DESCRIPTION = ""
    BOOL_OP = AND
    TEST_CLAUSE:
      TEST Contactsupp_positionName NOT_ATTRIBUTE_VALUE_NULL ""
      TEST Contactsupp_positionName NOT_ATTRIBUTE_IS_EMPTY ""
      TEST Contactsupp_positionName NOT_ATTRIBUTE_IS_MISSING ""
    PASSED -> DuplicateRemover_16
    PASSED -> XMLTemplater_10 [input 6]
voice: Tester
    TEST_MODE = Automatic
    TEST_DESCRIPTION = ""
    BOOL_OP = AND
    TEST_CLAUSE:
      TEST Contactsupp_voice NOT_ATTRIBUTE_VALUE_NULL ""
      TEST Contactsupp_voice NOT_ATTRIBUTE_IS_EMPTY ""
      TEST Contactsupp_voice NOT_ATTRIBUTE_IS_MISSING ""
    PASSED -> DuplicateRemover_16
    PASSED -> XMLTemplater_10 [input 7]
deliveryPoint: Tester
    TEST_MODE = Automatic
    TEST_DESCRIPTION = ""
    BOOL_OP = AND
    TEST_CLAUSE:
      TEST Contactsupp_deliveryPoint NOT_ATTRIBUTE_VALUE_NULL ""
      TEST Contactsupp_deliveryPoint NOT_ATTRIBUTE_IS_EMPTY ""
      TEST Contactsupp_deliveryPoint NOT_ATTRIBUTE_IS_MISSING ""
    PASSED -> DuplicateRemover_16
    PASSED -> XMLTemplater_10 [input 9]
city: Tester
    TEST_MODE = Automatic
    TEST_DESCRIPTION = ""
    BOOL_OP = AND
    TEST_CLAUSE:
      TEST Contactsupp_city NOT_ATTRIBUTE_VALUE_NULL ""
      TEST Contactsupp_city NOT_ATTRIBUTE_IS_EMPTY ""
      TEST Contactsupp_city NOT_ATTRIBUTE_IS_MISSING ""
    PASSED -> DuplicateRemover_16
    PASSED -> XMLTemplater_10 [input 10]
postalcode: Tester
    TEST_MODE = Automatic
    TEST_DESCRIPTION = ""
    BOOL_OP = AND
    TEST_CLAUSE:
      TEST Contactsupp_postalCode NOT_ATTRIBUTE_VALUE_NULL ""
      TEST Contactsupp_postalCode NOT_ATTRIBUTE_IS_EMPTY ""
      TEST Contactsupp_postalCode NOT_ATTRIBUTE_IS_MISSING ""
    PASSED -> DuplicateRemover_16
    PASSED -> DuplicateRemover_17
    PASSED -> XMLTemplater_10 [input 11]
country: Tester
    TEST_MODE = Automatic
    TEST_DESCRIPTION = ""
    BOOL_OP = AND
    TEST_CLAUSE:
      TEST Contactsupp_country NOT_ATTRIBUTE_VALUE_NULL ""
      TEST Contactsupp_country NOT_ATTRIBUTE_IS_EMPTY ""
      TEST Contactsupp_country NOT_ATTRIBUTE_IS_MISSING ""
    PASSED -> DuplicateRemover_16
    PASSED -> XMLTemplater_10 [input 12]
linkage: Tester
    TEST_MODE = Automatic
    TEST_DESCRIPTION = ""
    BOOL_OP = AND
    TEST_CLAUSE:
      TEST Contactsupp_linkage NOT_ATTRIBUTE_VALUE_NULL ""
      TEST Contactsupp_linkage NOT_ATTRIBUTE_IS_EMPTY ""
      TEST Contactsupp_linkage NOT_ATTRIBUTE_IS_MISSING ""
    PASSED -> DuplicateRemover_16
    PASSED -> DuplicateRemover_17
    PASSED -> XMLTemplater_10 [input 14]
protocole: Tester
    TEST_MODE = Automatic
    TEST_DESCRIPTION = ""
    BOOL_OP = AND
    TEST_CLAUSE:
      TEST Contactsupp_protocole NOT_ATTRIBUTE_VALUE_NULL ""
      TEST Contactsupp_protocole NOT_ATTRIBUTE_IS_EMPTY ""
      TEST Contactsupp_protocole NOT_ATTRIBUTE_IS_MISSING ""
    PASSED -> DuplicateRemover_16
    PASSED -> DuplicateRemover_17
    PASSED -> XMLTemplater_10 [input 15]
name: Tester
    TEST_MODE = Automatic
    TEST_DESCRIPTION = ""
    BOOL_OP = AND
    TEST_CLAUSE:
      TEST Contactsupp_name NOT_ATTRIBUTE_VALUE_NULL ""
      TEST Contactsupp_name NOT_ATTRIBUTE_IS_EMPTY ""
      TEST Contactsupp_name NOT_ATTRIBUTE_IS_MISSING ""
    PASSED -> DuplicateRemover_16
    PASSED -> DuplicateRemover_17
    PASSED -> XMLTemplater_10 [input 16]
description: Tester
    TEST_MODE = Automatic
    TEST_DESCRIPTION = ""
    BOOL_OP = AND
    TEST_CLAUSE:
      TEST Contactsupp_description NOT_ATTRIBUTE_VALUE_NULL ""
      TEST Contactsupp_description NOT_ATTRIBUTE_IS_EMPTY ""
      TEST Contactsupp_description NOT_ATTRIBUTE_IS_MISSING ""
    PASSED -> DuplicateRemover_16
    PASSED -> DuplicateRemover_17
    PASSED -> XMLTemplater_10 [input 17]
function: Tester
    TEST_MODE = Automatic
    TEST_DESCRIPTION = ""
    BOOL_OP = AND
    TEST_CLAUSE:
      TEST Contactsupp_function NOT_ATTRIBUTE_VALUE_NULL ""
      TEST Contactsupp_function NOT_ATTRIBUTE_IS_EMPTY ""
      TEST Contactsupp_function NOT_ATTRIBUTE_IS_MISSING ""
    PASSED -> DuplicateRemover_16
    PASSED -> DuplicateRemover_17
    PASSED -> XMLTemplater_10 [input 18]
DuplicateRemover_16
    KEYATTR = Contactsupp__count
    UNIQUE -> XMLTemplater_10 [input 5]
    UNIQUE -> DuplicateRemover_18
DuplicateRemover_17
    KEYATTR = Contactsupp__count
    UNIQUE -> XMLTemplater_10 [input 13]
    UNIQUE -> DuplicateRemover_18
DuplicateRemover_18
    KEYATTR = Contactsupp__count
    UNIQUE -> XMLTemplater_10 [input 1]
XMLTemplater_10
    GROUP_BY = Contactsupp__count
    POSTALCODE_QUERY_EXPR:
      <gmd:postalCode>
      			<gco:CharacterString>{fme:get-attribute("Contactsupp_postalCode")}</gco:CharacterString>
      </gmd:postalCode>
    POINT_CONTACT_QUERY_EXPR:
      <gmd:pointOfContact>
                      <rw:CI_ResponsibleParty gco:isoType="gmd:CI_ResponsibleParty">
      				{fme:process-features("INDIVIDUAL_NAME")}
                      {fme:process-features("ORGANISATION_NAME")}
                      {fme:process-features("POSITION_NAME")}


      					<gmd:contactInfo>
      						<gmd:CI_Contact>
      						{fme:process-features("VOICE")}
      							<gmd:address>
      								<gmd:CI_Address>

      									{fme:process-features("DELIVERY_POINT")}
      									{fme:process-features("CITY")}
      									{fme:process-features("POSTALCODE")}
      									{fme:process-features("COUNTRY")}
      									{fme:process-features("ADRESSE_MAIL")}
      								</gmd:CI_Address>
      							</gmd:address>
      							{fme:process-features("ONLINE_RESSOURCE")}
      						</gmd:CI_Contact>
      					</gmd:contactInfo>
      					{fme:process-features("ROLE")}

      				</rw:CI_ResponsibleParty>
                          </gmd:pointOfContact>
    ROOT_QUERY_EXPR:
          <?xml version="1.0" encoding="UTF-8"?>
      <rw:MD_Metadata xmlns:rw="http://metawal.wallonie.be/schemas/3.0" xmlns:gmd="http://www.isotc211.org/2005/gmd" xmlns:gts="http://www.isotc211.org/2005/gts" xmlns:gco="http://www.isotc211.org/2005/gco" xmlns:gml="http://www.opengis.net/gml" xmlns:geonet="http://www.fao.org/geonetwork" xmlns:xsi="http://www.w3.org/2001/XMLSchema-instance" gco:isoType="gmd:MD_Metadata" xsi:schemaLocation="http://metawal.wallonie.be/schemas/3.0 file:///H:/gimb14/c/c130606/data/schemas/rwschema.xsd">

      {fme:process-features("POINT_CONTACT")}

      </rw:MD_Metadata>
    POSITION_NAME_QUERY_EXPR:
      <gmd:positionName>
      		<gco:CharacterString>{fme:get-attribute("Contactsupp_positionName")}</gco:CharacterString>
      </gmd:positionName>
    PROTOCOL_QUERY_EXPR:
      <gmd:protocol>
      		<gco:CharacterString>{fme:get-attribute("Contactsupp_protocole")}</gco:CharacterString>
      </gmd:protocol>
    DESCRIPTION_QUERY_EXPR:
      	<gmd:description>
      				<gco:CharacterString>{fme:get-attribute("Contactsupp_description")}</gco:CharacterString>
      	</gmd:description>
    VISIBLE_QUERY_VALIDATE = Yes
    ADRESSE_MAIL_QUERY_EXPR:
      <gmd:electronicMailAddress>
      			<gco:CharacterString>{fme:get-attribute("Contactsupp_electronicMailAddress")}</gco:CharacterString>
      </gmd:electronicMailAddress>
    DELIVERY_POINT_QUERY_EXPR:
      	<gmd:deliveryPoint>
      		<gco:CharacterString>{fme:get-attribute("Contactsupp_deliveryPoint")}</gco:CharacterString>
      	</gmd:deliveryPoint>
    INDIVIDUAL_NAME_QUERY_EXPR:
      <gmd:individualName>
      		<gco:CharacterString>{fme:get-attribute("Contactsupp_individualName")}</gco:CharacterString>
      </gmd:individualName>
    COUNTRY_QUERY_EXPR:
      		<gmd:country>
      			<gco:CharacterString>{fme:get-attribute("Contactsupp_country")}</gco:CharacterString>
      		</gmd:country>
    ONLINE_RESSOURCE_QUERY_EXPR:
      	<gmd:onlineResource>
      				<gmd:CI_OnlineResource>
      						{fme:process-features("LINKAGE")}
      						{fme:process-features("PROTOCOL")}
      						{fme:process-features("NAME")}
      						{fme:process-features("DESCRIPTION")}
      						{fme:process-features("FUNCTION")}
      				</gmd:CI_OnlineResource>
          </gmd:onlineResource>
    VOICE_QUERY_EXPR:
      <gmd:phone>
      			<gmd:CI_Telephone>
      					<gmd:voice>
      							<gco:CharacterString>{fme:get-attribute("Contactsupp_voice")}</gco:CharacterString>
      					</gmd:voice>
      			</gmd:CI_Telephone>
      </gmd:phone>
    OUTPUT_XML_HEADER = Yes
    LINKAGE_QUERY_EXPR:
      	<gmd:linkage>
      				<gmd:URL>{fme:get-attribute("Contactsupp_linkage")}</gmd:URL>
      	</gmd:linkage>
    ORGANISATION_NAME_QUERY_EXPR:
       <gmd:organisationName>
      			<gco:CharacterString>{fme:get-attribute("Contactsupp_organisationName")}</gco:CharacterString>
      </gmd:organisationName>
    FUNCTION_QUERY_EXPR:
      	<gmd:function>
      			<gmd:CI_OnLineFunctionCode codeList="http://standards.iso.org/ittf/PubliclyAvailableStandards/ISO_19139_Schemas/resources/Codelist/ML_gmxCodelists.xml#CI_OnLineFunctionCode" codeListValue="{fme:get-attribute("Contactsupp_function")}"/>
      	</gmd:function>
    NAME_QUERY_EXPR:
      <gmd:name>
      			<gco:CharacterString>{fme:get-attribute("Contactsupp_name")}</gco:CharacterString>
      </gmd:name>
    ROLE_QUERY_EXPR:
      <gmd:role>
      		<gmd:CI_RoleCode codeList="http://standards.iso.org/ittf/PubliclyAvailableStandards/ISO_19139_Schemas/resources/Codelist/ML_gmxCodelists.xml#CI_RoleCode" codeListValue="{fme:get-attribute("Contactsupp_Role")}"/>
      </gmd:role>
    RESULT_ATTRIBUTE = _result
    CONSECUTIVE_GROUPS = No
    CITY_QUERY_EXPR:
      <gmd:city>
      			<gco:CharacterString>{fme:get-attribute("Contactsupp_city")}</gco:CharacterString>
      </gmd:city>
    -> modif_texte_8_StringReplacer_2_Output (output)
modif_texte_8_StringReplacer_2_Output (output)
