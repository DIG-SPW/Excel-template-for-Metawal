FME workspace DGO3_2.fmw

Parameters:
- Dossier_traitement = C:\Users\elise\Desktop\traitement
- Fichier_source = H:\gimb14\c\c130606\data\templates\Fiche_encodage_complete_DGO3.xlsm
- SourceDataset_MDB_ADO = H:\gimb14\c\c130606\data\DGO3\Extrait_TB_1.mdb   # Source Microsoft Access Database File(s)
- abreg_data =
- Description =
- nom_data =
- pers_matière =
- theme =
- DestDataset_XLSXW = C:\Users\elise\Desktop\fichier. xlsm   # Destination Microsoft Excel File
- Nom_fichier = fichier.xlsx   # Nom_Fichier

Readers:
- MDB_ADO_1: MDB_ADO from $(SourceDataset_MDB_ADO)

Writers:
- XLSXW_1: XLSXW to $(DestDataset_XLSXW)

Creator
    NUM = 1
    GEOMTYPE = Geometry Object
    CREATED -> ParameterFetcher
ParameterFetcher
    ATTR_LIST = abreg_data {$(abreg_data)} Description {$(Description)} nom_data {$(nom_data)} pers_matière {$(pers_matière)} theme {$(theme)}
    -> FeatureMerger [input 1]
THEMES (reader MDB_ADO_1)
    attributes: ID autonumber, theme text(50)
    -> AttributeRenamer
AttributeRenamer
    ATTR_LIST = theme,theme_def,""
    -> FeatureMerger [input 2]
FeatureMerger
    PROCESS_DUPS = No
    MERGE_TYPE = Attributes Only
    SUPPLIERS_FIRST = No
    JOIN_KEYS = @Value(theme) @Value(ID) AUTO
    SUPPLIER_PREFIX_DUMMY = YES
    NOT_MERGED -> AttributeCreator_6
    MERGED -> AttributeKeeper
AttributeCreator_6
    ATTR_LIST = theme_def,""
    -> AttributeKeeper
AttributeKeeper
    KEEP_ATTRS = abreg_data,nom_data,Description,pers_matière,theme_def
    -> FeatureMerger_2 [input 1]
PERSONNE (reader MDB_ADO_1)
    attributes: code_pers autonumber, nom text(50), prenom text(50), tel text(50), mail text(50), code_org long
    -> FeatureMerger_2 [input 2]
FeatureMerger_2
    PROCESS_DUPS = No
    MERGE_TYPE = Attributes Only
    SUPPLIERS_FIRST = No
    JOIN_KEYS = @Value(pers_matière) @Value(code_pers) AUTO
    SUPPLIER_PREFIX_DUMMY = YES
    NOT_MERGED -> AttributeCreator_4
    MERGED -> ParameterFetcher_2
AttributeCreator_4
    ATTR_LIST = nom,"",prenom,"",tel,"",mail,"",code_org,""
    -> ParameterFetcher_2
ParameterFetcher_2
    ATTR_LIST = Dossier_traitement {$(Dossier_traitement)}
    -> FilenamePartExtractor
FilenamePartExtractor
    SRC_ATTR = $(Fichier_source)
    FULLNAME_ATTR = _filename
    -> AttributeCreator
AttributeCreator
    ATTR_LIST = Nom_fichier,@Value(abreg_data).xlsm,nom,@Value(nom) @Value(prenom)
    -> AttributeCreator_2
AttributeCreator_2
    ATTR_LIST:
      Nom_fichier,@Value(abreg_data).xlsm,contenu,cd @Value(Dossier_traitement)
      rename @Value(_filename) @Value(Nom_fichier),Nom_fichier_data,@Value(abreg_data)_data
    -> PythonCaller
PythonCaller
    PYTHONSOURCE:
      import fmeobjects
      import os
      import shutil


      # Template Function interface:
      def traitement(feature):
         Nom_Fichier_sortie=feature.getAttribute("fichier_dataset")
         Fichier_source=FME_MacroValues['Fichier_source']
         Fichier_source_nom=feature.getAttribute("_filename")
         contenu=feature.getAttribute("contenu")
         Dossier_traitement=FME_MacroValues['Dossier_traitement']
         shutil.copy(Fichier_source,Dossier_traitement)
         os.chdir(Dossier_traitement)
         file = open("fichier.bat", "w")
         file.write(contenu)
         file.close()
         os.system("fichier.bat")
         os.remove("fichier.bat")
    PYTHONSYMBOL = traitement
    -> data_move (writer XLSXW_1)
data_move (writer XLSXW_1)
    attributes: nom_data string(20,format_type;Simple;font_type;;font_color;;fill_color;;custom_options;<Unused>), abreg_data string(20,format_type;Simple;font_type;;font_color;;fill_color;;custom_options;<Unused>), theme_def string(20,format_type;Simple;font_type;;font_color;;fill_color;;custom_options;;text_wrap;no), Description string(20,format_type;Simple;font_type;;font_color;;fill_color;;custom_options;;text_wrap;no), nom string(20,format_type;Simple;font_type;;font_color;;fill_color;;custom_options;;text_wrap;no), tel string(20,format_type;Simple;font_type;;font_color;;fill_color;;custom_options;;text_wrap;no), mail string(20,format_type;Simple;font_type;;font_color;;fill_color;;custom_options;;text_wrap;no)
