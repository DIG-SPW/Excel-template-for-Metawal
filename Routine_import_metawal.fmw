FME workspace Routine_import_metawal.fmw

Parameters:
- DestDataset_TEXTLINE = $(FME_MF_DIR)metawal_1508.xml   # Destination Text File
- SourceDataset_XLSXR = H:\gimb14\c\c130606\data\templates\Fiche_encodage_complete.xlsm   # Source Microsoft Excel File(s)

Readers:
- XLSXR_1: XLSXR from $(SourceDataset_XLSXR)

Writers:
- TEXTLINE_1: TEXTLINE to $(DestDataset_TEXTLINE)

synthese/INSPIRE (reader XLSXR_1)
    attributes: Nom char(79), Concernée par le théme char(4), Conforme au thème char(4), Traduction char(118), Date date
    -> AttributeCreator_12
    -> Tester_14
synthese/uselimitations (reader XLSXR_1)
    attributes: Uselimitations char(6)
    -> Tester_22
Tester_22
    TEST_MODE = Automatic
    TEST_DESCRIPTION = ""
    BOOL_OP = OR
    TEST_CLAUSE = TEST Uselimitations NOT_ATTRIBUTE_IS_EMPTY ""
    PASSED -> BulkAttributeRenamer_19
BulkAttributeRenamer_19
    REPLACE_STR = uselimitations_MD_Constraints
    ATTRCHOICE = All Attributes
    PATTERN_ACTION_DISP = Add String Prefix
    -> XMLTemplater [input 4]

Bookmark: INSPIRE
AttributeCreator_12
    ATTR_LIST = join,1
    -> FeatureMerger_2 [input 1]
Tester_14
    TEST_MODE = Automatic
    TEST_DESCRIPTION = ""
    BOOL_OP = OR
    TEST_CLAUSE = TEST @Value(Concernée par le théme) = Yes
    PASSED -> AttributeRenamer_2
    PASSED -> Tester
AttributeRenamer_2
    ATTR_LIST = Nom,Valeur,""
    -> AttributeCreator_2
AttributeCreator_2
    ATTR_LIST = Nom,GEMET - INSPIRE themes, version 1.0,Date,20080601,Type de date,publication
    -> DateFormatter_2
FeatureMerger_2
    PROCESS_DUPS = No
    MERGE_TYPE = Attributes Only
    SUPPLIERS_FIRST = No
    JOIN_KEYS = @Value(join) @Value(join) AUTO
    SUPPLIER_PREFIX_DUMMY = YES
    MERGED -> Tester_15
Tester_15
    TEST_MODE = Automatic
    TEST_DESCRIPTION = ""
    BOOL_OP = OR
    TEST_CLAUSE = TEST @Value(Valeur) = Yes
    PASSED -> Tester_16
Tester_16
    TEST_MODE = Automatic
    TEST_DESCRIPTION = ""
    BOOL_OP = OR
    TEST_CLAUSE = TEST @Value(Conforme au thème) = Yes
    PASSED -> DateFormatter_4
DateFormatter_4
    DATE_ATTR = Date
    FMT = ISO Date (%Y-%m-%d)
    SRCFMT = Unknown - Automatic Detection
    INVALID_DATE_VALUE = _FME_NO_OP_
    -> AttributeValueMapper_3
AttributeValueMapper_3
    DIRECTION = Forward (Source To Destination)
    VAL_ATTR = Conforme au thème
    LUT = Yes,true,No,false
    SRC = Conforme au thème
    -> BulkAttributeRenamer_11
BulkAttributeRenamer_11
    REPLACE_STR = inspire_
    ATTRCHOICE = All Attributes
    PATTERN_ACTION_DISP = Add String Prefix
    -> XMLTemplater [input 14]

Bookmark: Systeme_coordonnées_Inspire1
Tester
    TEST_MODE = Automatic
    TEST_DESCRIPTION = ""
    BOOL_OP = OR
    TEST_CLAUSE = TEST @Value(Date) = 20140417
    PASSED -> DuplicateRemover
DuplicateRemover
    KEYATTR = Date
    UNIQUE -> XMLTemplater [input 3]

Bookmark: Scope INSPIRE
synthese/ScopeINSPIRE (reader XLSXR_1)
    attributes: Nom char(14), Valeur char(4)
    -> AttributeCreator_11
AttributeCreator_11
    ATTR_LIST = join,1
    -> FeatureMerger_2 [input 2]

Bookmark: Point de contact
synthese/pt_contact (reader XLSXR_1)
    attributes: Role char(61), organisationName char(27), electronicMailAddress char(31), individualName char(4), positionName char(3), voice char(13), deliveryPoint char(14), city char(7), postalCode number(5,0), country char(9), linkage char(36), protocole char(24), name char(26), description char(20), function char(20)
    -> AttributeSplitter_3
AttributeSplitter_3
    LIST_NAME = _list
    ATTR_NAME = Role
    DELIMITER = ;
    TRIM_OPTION = Both
    DROP_EMPTY_PARTS = No
    -> ListExploder_3
ListExploder_3
    INDEX_ATTR = _element_index
    MODE = List Elements and Original Attributes
    LIST_ATTR = _list{}
    LIST_FOUND -> AttributeCopier
AttributeCopier
    ATTR_LIST = _list,Role_type,""
    -> AttributeRenamer
AttributeRenamer
    ATTR_LIST = _list,Role,""
    -> AttributeValueMapper
AttributeValueMapper
    DIRECTION = Forward (Source To Destination)
    VAL_ATTR = Role
    LUT = A l'origine de,originator,Point de contact (fiche),pointOfContact,Point de contact (ressource),pointOfContact,Point de recherche,principalInvestigator,Auteur,author,Distributeur,distributor,Editeur,publisher,Exécutant,processor,Fournisseur,resourceProvider,Gestionnaire,custodian,Propriétaire,owner,Utilisateur,user
    SRC = Role
    -> Tester_2
Tester_2
    TEST_MODE = Automatic
    TEST_DESCRIPTION = ""
    BOOL_OP = OR
    TEST_CLAUSE:
      TEST @Value(Role) = Role
      TEST Role ATTRIBUTE_IS_EMPTY ""
    FAILED -> TestFilter
TestFilter
    TEST_LIST = BOOL_OP,OR,COMPOSITE_TEST,<Unused>,TEST_CLAUSE,"TEST @Value(Role_type) = Point de contact (fiche)",Point de contact (fiche),BOOL_OP,OR,COMPOSITE_TEST,<Unused>,TEST_CLAUSE,"TEST @Value(Role_type) = Distributeur",Distributeur
    DEFAULT_VALUE = Autre
    Autre -> BulkAttributeRenamer
    Point de contact (fiche) -> AttributeCreator_9
    Distributeur -> FeatureMerger_3 [input 2]
    Distributeur -> FeatureMerger_4 [input 2]
AttributeCreator_9
    ATTR_LIST = join,1
    -> FeatureMerger [input 1]
BulkAttributeRenamer
    REPLACE_STR = Contactsupp_
    ATTRCHOICE = All Attributes
    PATTERN_ACTION_DISP = Add String Prefix
    -> XMLTemplater [input 2]
FeatureMerger
    PROCESS_DUPS = No
    MERGE_TYPE = Attributes Only
    SUPPLIERS_FIRST = No
    JOIN_KEYS = @Value(join) @Value(join) AUTO
    SUPPLIER_PREFIX_DUMMY = YES
    MERGED -> BulkAttributeRenamer_9
BulkAttributeRenamer_9
    REPLACE_STR = ContactMetadata_
    ATTRCHOICE = All Attributes
    PATTERN_ACTION_DISP = Add String Prefix
    -> XMLTemplater [input 15]

Bookmark: Régime d'accés à la ressource (Acces Constraint and OtherConstraints)
synthese/service_visusalisation (reader XLSXR_1)
    attributes: Coché char(4), Valeur char(67)
    -> Tester_20
Tester_20
    TEST_MODE = Automatic
    TEST_DESCRIPTION = ""
    BOOL_OP = OR
    TEST_CLAUSE = TEST @Value(Coché) = Yes
    PASSED -> AttributeRenamer_4
AttributeRenamer_4
    ATTR_LIST = Valeur,OtherConstraints,""
    -> BulkAttributeRenamer_17
BulkAttributeRenamer_17
    REPLACE_STR = regime_acces_ressource
    ATTRCHOICE = All Attributes
    PATTERN_ACTION_DISP = Add String Prefix
    -> XMLTemplater [input 7]
synthese/regime_acces_ressource (reader XLSXR_1)
    attributes: Coché char(5), AccessConstraints char(20), Phrase char(111), Valeur char(104)
    -> Tester_8
Tester_8
    TEST_MODE = Automatic
    TEST_DESCRIPTION = ""
    BOOL_OP = OR
    TEST_CLAUSE:
      TEST @Value(Coché) = Yes
      TEST @Value(Coché) = TRUE
    PASSED -> AttributeCreator_13
AttributeCreator_13
    ATTR_LIST = OtherConstraints,@Value(Phrase) @Value(Valeur)
    -> BulkAttributeRenamer_15
BulkAttributeRenamer_15
    REPLACE_STR = regime_acces_ressource
    ATTRCHOICE = All Attributes
    PATTERN_ACTION_DISP = Add String Prefix
    -> XMLTemplater [input 9]
    -> XMLTemplater [input 7]

Bookmark: Synthese
synthese/principal (reader XLSXR_1)
    attributes: ID number(2,0), parentIdentifier char(37), hierarchyLevel char(8), hierarchyLevelName char(8), title char(6), alternateTitle char(18), acronym char(8), versionYear char(12), AOI char(4), creation_date date, publication_date char(11), revision_date char(11), localCode char(17), abstract char(14), abstract_body char(10), status char(10), maintenanceAndUpdateFrequency char(9), maintenanceNote char(10), fileName char(35), fileDescription char(37), fileType char(4), spatialRepresentationType char(7), beginPosition char(11), endPosition char(11), statementLineage char(99), INSPIREConformity char(13), nameOfMeasure char(20), consistencyTitle char(8), consistencyAlternateTitle string, consistencyCode string,
      consistencyDescription string, evaluationMethodType string, dateTime string, conformanceTitle char(250), conformanceAlternateTitle string, conformanceDate char(11), conformanceDateType char(12), conformanceExplanation char(47), conformancePass char(6), quantitativeResultValue string, characterSet char(5), metadataStandardName char(10), metadataStandardVersion char(16), CodeSpace char(46), metadata_lang char(4), referenceSystemCode number(6,0), CodeSpaceReferenceSystem char(21), Version char(6), language char(4), characterSetRessource char(5), spatialDescription char(16), westBoundLongitude number(4,2), eastBoundLongitude number(3,1), southBoundLatitude number(5,2), northBoundLatitude number(5,2), minimumValue char(4), maximumValue char(5), level char(8), classification char(13), useLimitation1 char(9),
      useLimitation2 string, accessConstraints string, useConstraints string, otherConstraints1 string, otherConstraints2 string, useLimitation3 string, useLimitation4 string
    -> TimeStamper
    -> AttributeKeeper_2
    -> AttributeKeeper
AttributeKeeper_2
    KEEP_ATTRS = alternateTitle
    -> AttributeSplitter_4
AttributeSplitter_4
    LIST_NAME = _list
    ATTR_NAME = alternateTitle
    DELIMITER = ;
    TRIM_OPTION = Both
    DROP_EMPTY_PARTS = No
    -> ListExploder_4
ListExploder_4
    INDEX_ATTR = _element_index
    MODE = List Elements and Original Attributes
    LIST_ATTR = _list{}
    LIST_FOUND -> AttributeCopier_2
AttributeCopier_2
    ATTR_LIST = _list,alternateTitle,""
    -> BulkAttributeRenamer_10
BulkAttributeRenamer_10
    REPLACE_STR = AlternateTitle_
    ATTRCHOICE = All Attributes
    PATTERN_ACTION_DISP = Add String Prefix
    -> XMLTemplater [input 23]
TimeStamper
    FMT = XML DateTime (^Y-^m-^dT^H:^M:^S)
    TIME_ATTR = _timestamp
    -> DateFormatter
DateFormatter
    DATE_ATTR = creation_date,publication_date,revision_date,beginPosition,endPosition,conformanceDate
    FMT = ISO Date (%Y-%m-%d)
    SRCFMT = Unknown - Automatic Detection
    INVALID_DATE_VALUE = _FME_NO_OP_
    -> DateFormatter_3
DateFormatter_3
    DATE_ATTR = dateTime
    FMT = ISO DateTime (%Y-%m-%dT%H:%M:%S)
    SRCFMT = Unknown - Automatic Detection
    INVALID_DATE_VALUE = _FME_NO_OP_
    -> AttributeCreator_3
AttributeCreator_3
    ATTR_LIST:
      abstract,@Value(abstract)
      @Value(abstract_body)
    -> Tester_10
Tester_10
    TEST_MODE = Automatic
    TEST_DESCRIPTION = ""
    BOOL_OP = OR
    TEST_CLAUSE = TEST acronym NOT_ATTRIBUTE_IS_MISSING ""
    PASSED -> AttributeCreator_4
    FAILED -> Tester_11
AttributeCreator_4
    ATTR_LIST = acronym,(@Value(acronym))
    -> Tester_11
Tester_11
    TEST_MODE = Automatic
    TEST_DESCRIPTION = ""
    BOOL_OP = OR
    TEST_CLAUSE = TEST AOI NOT_ATTRIBUTE_IS_MISSING ""
    PASSED -> AttributeCreator_5
    FAILED -> Tester_12
AttributeCreator_5
    ATTR_LIST = AOI,[@Value(AOI)]
    -> Tester_12
Tester_12
    TEST_MODE = Automatic
    TEST_DESCRIPTION = ""
    BOOL_OP = OR
    TEST_CLAUSE = TEST versionYear NOT_ATTRIBUTE_IS_MISSING ""
    PASSED -> AttributeCreator_6
    FAILED -> AttributeCreator_7
AttributeCreator_6
    ATTR_LIST = versionYear,_@Value(versionYear)
    -> AttributeCreator_7
AttributeCreator_7
    ATTR_LIST = title,@Value(title)@Value(AOI)@Value(acronym)@Value(versionYear),organisationName_owner,Service Public de Wallonie,electronicMailAddress_owner,helpdesk.carto@spw.wallonie.be,linkage_owner,http://www.cartographie.wallonie.be,protocole_owner,WWW:LINK-1.0-http--link,name_owner,Géoportail de la Wallonie,Role_owner,owner
    -> XMLTemplater [input 1]
AttributeKeeper
    KEEP_ATTRS = metadata_lang
    -> AttributeCreator_8
AttributeCreator_8
    ATTR_LIST = join,1
    -> FeatureMerger [input 2]

Bookmark: Keywords
synthese/keywords2 (reader XLSXR_1)
    attributes: Keywords char(16), Nom char(41), Valeur char(109), Date char(11), Type de date char(12)
    -> Tester_3
Tester_3
    TEST_MODE = Automatic
    TEST_DESCRIPTION = ""
    BOOL_OP = OR
    TEST_CLAUSE:
      TEST @Value(Nom) = Nom
      TEST Valeur ATTRIBUTE_IS_MISSING ""
      TEST Valeur ATTRIBUTE_IS_EMPTY ""
    FAILED -> AttributeSplitter_5
AttributeSplitter_5
    LIST_NAME = _list
    ATTR_NAME = Valeur
    DELIMITER = ;
    TRIM_OPTION = Both
    DROP_EMPTY_PARTS = No
    -> ListExploder_5
ListExploder_5
    INDEX_ATTR = _element_index
    MODE = List Elements and Original Attributes
    LIST_ATTR = _list{}
    LIST_FOUND -> AttributeCreator_10
AttributeCreator_10
    ATTR_LIST = Valeur,@Value(_list)
    -> DateFormatter_2
DateFormatter_2
    DATE_ATTR = Date
    FMT = ISO Date (%Y-%m-%d)
    SRCFMT = Unknown - Automatic Detection
    INVALID_DATE_VALUE = _FME_NO_OP_
    -> Tester_13
Tester_13
    TEST_MODE = Automatic
    TEST_DESCRIPTION = ""
    BOOL_OP = OR
    TEST_CLAUSE = TEST @Value(Keywords) = Keywordfree
    FAILED -> BulkAttributeRenamer_2
    PASSED -> BulkAttributeRenamer_3
BulkAttributeRenamer_2
    REPLACE_STR = Keywords_
    ATTRCHOICE = All Attributes
    PATTERN_ACTION_DISP = Add String Prefix
    -> XMLTemplater [input 22]
BulkAttributeRenamer_3
    REPLACE_STR = Keywordsfree_
    ATTRCHOICE = All Attributes
    PATTERN_ACTION_DISP = Add String Prefix
    -> XMLTemplater [input 21]

Bookmark: ISO
synthese/ISO_Topic (reader XLSXR_1)
    attributes: Nom char(17), Valeur char(76)
    -> Tester_5
Tester_5
    TEST_MODE = Automatic
    TEST_DESCRIPTION = ""
    BOOL_OP = OR
    TEST_CLAUSE:
      TEST @Value(Valeur) = Valeur
      TEST Valeur ATTRIBUTE_IS_MISSING ""
    FAILED -> AttributeSplitter
AttributeSplitter
    LIST_NAME = _list
    ATTR_NAME = Valeur
    DELIMITER = ;
    TRIM_OPTION = Both
    DROP_EMPTY_PARTS = No
    -> ListExploder
ListExploder
    INDEX_ATTR = _element_index
    MODE = List Elements and Original Attributes
    LIST_ATTR = _list{}
    LIST_FOUND -> AttributeCreator
AttributeCreator
    ATTR_LIST = Valeur,@Value(_list)
    -> AttributeValueMapper_2
AttributeValueMapper_2
    DIRECTION = Forward (Source To Destination)
    VAL_ATTR = Valeur
    LUT = Biologie, faune et flore,biota,Cadastre, aménagement,planningCadastre,Carte de référence de la couverture terrestre,imageryBaseMapsEarthCover,Climatologie, météorologie,climatologyMeteorologyAtmospher,Constructions et ouvrages,structure,Eaux intérieures, hydrographie,inlandWaters,Infrastructures de transport,transportation,Infrastructures militaires,intelligenceMilitary,Limites politiques et administratives,boundaries,Sciences de la terre, géosciences,geoscientificInformation,Télécommunication, approvisionnement et énergie,utilitiesCommunication,Agriculture,farming,Altimétrie,elevation,Economie,economy,Environnement,environment,Localisation,location,Océans,oceans,Santé,health,Société,society
    SRC = Valeur
    -> BulkAttributeRenamer_4
BulkAttributeRenamer_4
    REPLACE_STR = ISO_
    ATTRCHOICE = All Attributes
    PATTERN_ACTION_DISP = Add String Prefix
    -> XMLTemplater [input 20]

Bookmark: Denominator Distance
synthese/Distance (reader XLSXR_1)
    attributes: Nom char(9), Valeur string
    -> Tester_7
Tester_7
    TEST_MODE = Automatic
    TEST_DESCRIPTION = ""
    BOOL_OP = OR
    TEST_CLAUSE:
      TEST @Value(Valeur) = Valeur
      TEST Valeur ATTRIBUTE_IS_EMPTY ""
    FAILED -> BulkAttributeRenamer_6
BulkAttributeRenamer_6
    REPLACE_STR = Distance_
    ATTRCHOICE = All Attributes
    PATTERN_ACTION_DISP = Add String Prefix
    -> XMLTemplater [input 19]
synthese/denominator (reader XLSXR_1)
    attributes: Nom char(12), Valeur number(6,0)
    -> Tester_6
Tester_6
    TEST_MODE = Automatic
    TEST_DESCRIPTION = ""
    BOOL_OP = OR
    TEST_CLAUSE:
      TEST @Value(Valeur) = Valeur
      TEST Valeur ATTRIBUTE_IS_EMPTY ""
    FAILED -> BulkAttributeRenamer_5
BulkAttributeRenamer_5
    REPLACE_STR = Denominator_
    ATTRCHOICE = All Attributes
    PATTERN_ACTION_DISP = Add String Prefix
    -> XMLTemplater [input 18]

Bookmark: Distribution
synthese/online_full (reader XLSXR_1)
    attributes: Distributeur char(27), orderingInstructions1 char(108), nameformat1 char(30), versionFormat1 number(3,0), transfersize1 (créer bloc xml) number(3,0), dirstributionURLdl char(31), distributionProtocoldl char(22), distributionNamedl char(42), distributionDescriptiodl char(32), distributionFunctiodl char(9), Element_ISO char(5)
    -> FeatureMerger_3 [input 1]
FeatureMerger_3
    PROCESS_DUPS = No
    MERGE_TYPE = Attributes Only
    SUPPLIERS_FIRST = No
    JOIN_KEYS = @Value(Distributeur) @Value(organisationName) AUTO
    SUPPLIER_PREFIX_DUMMY = YES
    MERGED -> BulkAttributeRenamer_7
BulkAttributeRenamer_7
    REPLACE_STR = Distributiononline_
    ATTRCHOICE = All Attributes
    PATTERN_ACTION_DISP = Add String Prefix
    -> XMLTemplater [input 17]
synthese/acces_limite (reader XLSXR_1)
    attributes: dirstributionURLApp char(6), distributionProtocolApp string, distributionNameApp string, distributionDescriptioApp string, distributionFunctioApp char(7), Element_ISO string
    -> BulkAttributeRenamer_12
synthese/site_rapport (reader XLSXR_1)
    attributes: dirstributionURLsit char(5), distributionProtocolsit string, distributionNamesit string, distributionDescriptiosit string, distributionFunctiosit char(12)
    -> AttributeRenamer_3
AttributeRenamer_3
    ATTR_LIST = dirstributionURLsit,dirstributionURLApp,"",distributionDescriptiosit,distributionDescriptioApp,"",distributionFunctiosit,distributionFunctioApp,"",distributionNamesit,distributionNameApp,"",distributionProtocolsit,distributionProtocolApp,""
    -> BulkAttributeRenamer_12
BulkAttributeRenamer_12
    REPLACE_STR = Distributionacceslimite_
    ATTRCHOICE = All Attributes
    PATTERN_ACTION_DISP = Add String Prefix
    -> XMLTemplater [input 13]
synthese/offline (reader XLSXR_1)
    attributes: Distributeur char(27), orderingInstructions3 char(108), nameformat3 char(30), versionFormat3 number(3,0), transfersize3 (créer bloc xml) number(3,0), mediumName char(8), mediumNameCode char(9)
    -> FeatureMerger_4 [input 1]
FeatureMerger_4
    PROCESS_DUPS = No
    MERGE_TYPE = Attributes Only
    SUPPLIERS_FIRST = No
    JOIN_KEYS = @Value(Distributeur) @Value(organisationName) AUTO
    SUPPLIER_PREFIX_DUMMY = YES
    MERGED -> BulkAttributeRenamer_13
BulkAttributeRenamer_13
    REPLACE_STR = DistributionOffLine_
    ATTRCHOICE = All Attributes
    PATTERN_ACTION_DISP = Add String Prefix
    -> XMLTemplater [input 12]

Bookmark: Hierarchy level
synthese/hierachy_level2 (reader XLSXR_1)
    attributes: Nom char(19), Valeur char(8)
    -> Tester_9
Tester_9
    TEST_MODE = Automatic
    TEST_DESCRIPTION = ""
    BOOL_OP = OR
    TEST_CLAUSE:
      TEST @Value(Nom) = Nom
      TEST Valeur ATTRIBUTE_IS_EMPTY ""
    FAILED -> BulkAttributeRenamer_8
BulkAttributeRenamer_8
    REPLACE_STR = hierarchylevel_
    ATTRCHOICE = All Attributes
    PATTERN_ACTION_DISP = Add String Prefix
    -> XMLTemplater [input 16]

Bookmark: Conformance pass
synthese/conformance_pass (reader XLSXR_1)
    attributes: Nom char(16), Valeur char(12)
    -> Tester_4
Tester_4
    TEST_MODE = Automatic
    TEST_DESCRIPTION = ""
    BOOL_OP = OR
    TEST_CLAUSE = TEST @Value(Valeur) = Pas évaluée
    FAILED -> BulkAttributeRenamer_14
    PASSED -> XMLTemplater [input 11]
BulkAttributeRenamer_14
    REPLACE_STR = Conformance_pass
    ATTRCHOICE = All Attributes
    PATTERN_ACTION_DISP = Add String Prefix
    -> XMLTemplater [input 10]

Bookmark: conditions d'utilisation
synthese/conditions_utilisations (reader XLSXR_1)
    attributes: Coché char(3), UsecConstraints char(20), Partie 1 char(248), Valeur1 char(268), Partie 2 char(25), Valeur 2 string
    -> Tester_21
Tester_21
    TEST_MODE = Automatic
    TEST_DESCRIPTION = ""
    BOOL_OP = OR
    TEST_CLAUSE = TEST @Value(Coché) = Yes
    PASSED -> AttributeCreator_15
AttributeCreator_15
    ATTR_LIST = Valeur_comp,@Value(Partie 1)@Value(Valeur1)@Value(Partie 2)@Value(Valeur 2)
    -> BulkAttributeRenamer_18
BulkAttributeRenamer_18
    REPLACE_STR = uselimitations
    ATTRCHOICE = All Attributes
    PATTERN_ACTION_DISP = Add String Prefix
    -> XMLTemplater [input 6]
    -> XMLTemplater [input 5]

Bookmark: Local Code
synthese/Local_Code (reader XLSXR_1)
    attributes: id number(2,0), Valeur1 char(17), Valeur2 char(5), Valeur3 char(5)
    -> Tester_17
Tester_17
    TEST_MODE = Automatic
    TEST_DESCRIPTION = ""
    BOOL_OP = OR
    TEST_CLAUSE = TEST @Value(id) = 2
    PASSED -> Tester_18
    FAILED -> Tester_19
Tester_18
    TEST_MODE = Automatic
    TEST_DESCRIPTION = ""
    BOOL_OP = OR
    TEST_CLAUSE = TEST Valeur1 NOT_ATTRIBUTE_IS_EMPTY ""
    PASSED -> BulkAttributeRenamer_16
Tester_19
    TEST_MODE = Automatic
    TEST_DESCRIPTION = ""
    BOOL_OP = OR
    TEST_CLAUSE = TEST Valeur1 NOT_ATTRIBUTE_IS_EMPTY ""
    PASSED -> AttributeCreator_14
AttributeCreator_14
    ATTR_LIST = Valeur1,@Value(Valeur1)_@Value(Valeur2)_@Value(Valeur3)
    -> BulkAttributeRenamer_16
BulkAttributeRenamer_16
    REPLACE_STR = local_code
    ATTRCHOICE = All Attributes
    PATTERN_ACTION_DISP = Add String Prefix
    -> XMLTemplater [input 8]

Bookmark: OUTPUT
XMLTemplater
    CONFORMANCEPASS_EVALUEE_QUERY_EXPR = <gmd:pass><gco:Boolean>{fme:get-attribute("Conformance_passValeur")}</gco:Boolean></gmd:pass>
    ALTERNATE_TITLE_QUERY_EXPR:
      <gmd:alternateTitle>
      		<gco:CharacterString>{fme:get-attribute("AlternateTitle_alternateTitle")}</gco:CharacterString>
      </gmd:alternateTitle>
    ROOT_QUERY_EXPR:
      <?xml version="1.0" encoding="UTF-8"?>
      <rw:MD_Metadata xmlns:rw="http://metawal.wallonie.be/schemas/3.0" xmlns:gmd="http://www.isotc211.org/2005/gmd" xmlns:gts="http://www.isotc211.org/2005/gts" xmlns:gco="http://www.isotc211.org/2005/gco" xmlns:gml="http://www.opengis.net/gml" xmlns:geonet="http://www.fao.org/geonetwork" xmlns:xsi="http://www.w3.org/2001/XMLSchema-instance" gco:isoType="gmd:MD_Metadata" xsi:schemaLocation="http://metawal.wallonie.be/schemas/3.0 file:///H:/gimb14/c/c130606/data/schemas/rwschema.xsd">
      	<gmd:fileIdentifier>
      		<gco:CharacterString></gco:CharacterString>
      	</gmd:fileIdentifier>
      	<gmd:language>
      		<gco:CharacterString>{fme:get-attribute("metadata_lang")}</gco:CharacterString>
      	</gmd:language>
      	<gmd:characterSet>
      		<gmd:MD_CharacterSetCode codeListValue="{fme:get-attribute("characterSet")}" codeList="http://standards.iso.org/ittf/PubliclyAvailableStandards/ISO_19139_Schemas/resources/Codelist/ML_gmxCodelists.xml#MD_CharacterSetCode"/>
      	</gmd:characterSet>
          <gmd:parentIdentifier>
              <gco:CharacterString>{fme:get-attribute("parentIdentifier")}</gco:CharacterString>
          </gmd:parentIdentifier>
      	<gmd:hierarchyLevel>
      		<gmd:MD_ScopeCode codeList="http://standards.iso.org/ittf/PubliclyAvailableStandards/ISO_19139_Schemas/resources/Codelist/ML_gmxCodelists.xml#MD_ScopeCode" codeListValue="{fme:get-attribute("hierarchyLevel")}"/>
      	</gmd:hierarchyLevel>
          {fme:process-features("HIERARCHYLEVEL")}

      	{fme:process-features("CONTACT_METADATA")}

      	<gmd:dateStamp>
      		<gco:DateTime>{fme:get-attribute("_timestamp")}</gco:DateTime>
      	</gmd:dateStamp>
      	<gmd:metadataStandardName>
      		<gco:CharacterString>{fme:get-attribute("metadataStandardName")}</gco:CharacterString>
      	</gmd:metadataStandardName>
      	<gmd:metadataStandardVersion>
      		<gco:CharacterString>{fme:get-attribute("metadataStandardVersion")}</gco:CharacterString>
      	</gmd:metadataStandardVersion>
          {fme:process-features("SYST_COORD_INSPIRE1")}
      	<gmd:referenceSystemInfo>
      		<gmd:MD_ReferenceSystem>
      			<gmd:referenceSystemIdentifier>
      				<gmd:RS_Identifier>
      					<gmd:code>
      						<gco:CharacterString>{fme:get-attribute("referenceSystemCode")}</gco:CharacterString>
      					</gmd:code>
      					<gmd:codeSpace>
      						<gco:CharacterString>{fme:get-attribute("CodeSpaceReferenceSystem")}</gco:CharacterString>
      					</gmd:codeSpace>
      				</gmd:RS_Identifier>
      			</gmd:referenceSystemIdentifier>
      		</gmd:MD_ReferenceSystem>
      	</gmd:referenceSystemInfo>
      	<gmd:identificationInfo>
      		<gmd:MD_DataIdentification>
      			<gmd:citation>
      				<gmd:CI_Citation>
      					<gmd:title>
      						<gco:CharacterString>{fme:get-attribute("title")}</gco:CharacterString>
      					</gmd:title>
      {fme:process-features("ALTERNATE_TITLE")}
      					<gmd:date>
      						<gmd:CI_Date>
      							<gmd:date>
      								<gco:Date>{fme:get-attribute("creation_date")}</gco:Date>
      							</gmd:date>
      							<gmd:dateType>
      								<gmd:CI_DateTypeCode codeListValue="creation" codeList="http://standards.iso.org/ittf/PubliclyAvailableStandards/ISO_19139_Schemas/resources/Codelist/ML_gmxCodelists.xml#CI_DateTypeCode"/>
      							</gmd:dateType>
      						</gmd:CI_Date>
      					</gmd:date>
      					<gmd:date>
      						<gmd:CI_Date>
      							<gmd:date>
      								<gco:Date>{fme:get-attribute("revision_date")}</gco:Date>
      							</gmd:date>
      							<gmd:dateType>
      								<gmd:CI_DateTypeCode codeList="http://standards.iso.org/ittf/PubliclyAvailableStandards/ISO_19139_Schemas/resources/Codelist/ML_gmxCodelists.xml#CI_DateTypeCode" codeListValue="revision"/>
      							</gmd:dateType>
      						</gmd:CI_Date>
      					</gmd:date>
      					<gmd:date>
      						<gmd:CI_Date>
      							<gmd:date>
      								<gco:Date>{fme:get-attribute("publication_date")}</gco:Date>
      							</gmd:date>
      							<gmd:dateType>
      								<gmd:CI_DateTypeCode codeList="http://standards.iso.org/ittf/PubliclyAvailableStandards/ISO_19139_Schemas/resources/Codelist/ML_gmxCodelists.xml#CI_DateTypeCode" codeListValue="publication"/>
      							</gmd:dateType>
      						</gmd:CI_Date>
      					</gmd:date>

                        {fme:process-features("LOCALCODE")}


      					<gmd:identifier>
      						<gmd:RS_Identifier>

                              <gmd:code>
      								<gco:CharacterString></gco:CharacterString>
      							</gmd:code>
      							<gmd:codeSpace>
      								<gco:CharacterString>{fme:get-attribute("CodeSpace")}</gco:CharacterString>
      							</gmd:codeSpace>
      						</gmd:RS_Identifier>
      					</gmd:identifier>
      				</gmd:CI_Citation>
      			</gmd:citation>
      			<gmd:abstract>
      				<gco:CharacterString>{fme:get-attribute("abstract")}</gco:CharacterString>
      			</gmd:abstract>
      			<gmd:status>
      				<gmd:MD_ProgressCode codeList="http://standards.iso.org/ittf/PubliclyAvailableStandards/ISO_19139_Schemas/resources/Codelist/ML_gmxCodelists.xml#MD_ProgressCode" codeListValue="{fme:get-attribute("status")}"/>
      			</gmd:status>


      			<gmd:pointOfContact>
      				<rw:CI_ResponsibleParty gco:isoType="gmd:CI_ResponsibleParty">
      					<gmd:organisationName>
      						<gco:CharacterString>{fme:get-attribute("organisationName_owner")}</gco:CharacterString>
      					</gmd:organisationName>
      					<gmd:contactInfo>
      						<gmd:CI_Contact>
      							<gmd:address>
      								<gmd:CI_Address>
      									<gmd:electronicMailAddress>
      										<gco:CharacterString>{fme:get-attribute("electronicMailAddress_owner")}</gco:CharacterString>
      									</gmd:electronicMailAddress>
      								</gmd:CI_Address>
      							</gmd:address>
      							<gmd:onlineResource>
      								<gmd:CI_OnlineResource>
      									<gmd:linkage>
      										<gmd:URL>{fme:get-attribute("linkage_owner")}</gmd:URL>
      									</gmd:linkage>
      									<gmd:protocol>
      										<gco:CharacterString>{fme:get-attribute("protocole_owner")}</gco:CharacterString>
      									</gmd:protocol>
      									<gmd:name>
      										<gco:CharacterString>{fme:get-attribute("name_owner")}</gco:CharacterString>
      									</gmd:name>
      								</gmd:CI_OnlineResource>
      							</gmd:onlineResource>
      						</gmd:CI_Contact>
      					</gmd:contactInfo>
      					<gmd:role>
      						<gmd:CI_RoleCode codeListValue="{fme:get-attribute("Role_owner")}" codeList="http://standards.iso.org/ittf/PubliclyAvailableStandards/ISO_19139_Schemas/resources/Codelist/ML_gmxCodelists.xml#CI_RoleCode"/>
      					</gmd:role>
      				</rw:CI_ResponsibleParty>
                          </gmd:pointOfContact>

                        {fme:process-features("CONTACT")}

      			<gmd:resourceMaintenance>
      				<gmd:MD_MaintenanceInformation>
      					<gmd:maintenanceAndUpdateFrequency>
      						<gmd:MD_MaintenanceFrequencyCode codeList="http://standards.iso.org/ittf/PubliclyAvailableStandards/ISO_19139_Schemas/resources/Codelist/ML_gmxCodelists.xml#MD_MaintenanceFrequencyCode" codeListValue="{fme:get-attribute("maintenanceAndUpdateFrequency")}"/>
      					</gmd:maintenanceAndUpdateFrequency>
      					<gmd:maintenanceNote>
                          <gco:CharacterString>{fme:get-attribute("maintenanceNote")}</gco:CharacterString>
                          </gmd:maintenanceNote>
      				</gmd:MD_MaintenanceInformation>
      			</gmd:resourceMaintenance>
      			<gmd:graphicOverview xmlns:srv="http://www.isotc211.org/2005/srv">
      				<gmd:MD_BrowseGraphic>
      					<gmd:fileName>
      						<gco:CharacterString>{fme:get-attribute("fileName")}</gco:CharacterString>
      					</gmd:fileName>
      					<gmd:fileDescription>
      						<gco:CharacterString>{fme:get-attribute("fileDescription")}</gco:CharacterString>
      					</gmd:fileDescription>
      					<gmd:fileType>
      						<gco:CharacterString>{fme:get-attribute("fileType")}</gco:CharacterString>
      					</gmd:fileType>
      				</gmd:MD_BrowseGraphic>
      			</gmd:graphicOverview>

      			{fme:process-features("KEYWORDS_FREE")}

      			{fme:process-features("KEYWORDS")}

      	<gmd:resourceConstraints>
      		<gmd:MD_LegalConstraints>

      {fme:process-features("USELIMITATION")}
      {fme:process-features("ACCESS_CONSTRAINT")}
      {fme:process-features("USECONSTRAINTS")}
      {fme:process-features("OTHER_CONSTRAINTS")}






      		</gmd:MD_LegalConstraints>
      	</gmd:resourceConstraints>
      	<gmd:resourceConstraints>

          <gmd:MD_Constraints>
          {fme:process-features("MD_CONSTRAINTS_USELIMITATION")}
          </gmd:MD_Constraints>
          </gmd:resourceConstraints>
          		<gmd:resourceConstraints>

      		<gmd:MD_SecurityConstraints>
      			<gmd:useLimitation>
      				<gco:CharacterString>{fme:get-attribute("useLimitation1")}</gco:CharacterString>
      			</gmd:useLimitation>
                  <gmd:classification>
      				<gmd:MD_ClassificationCode codeList="http://standards.iso.org/ittf/PubliclyAvailableStandards/ISO_19139_Schemas/resources/Codelist/ML_gmxCodelists.xml#MD_ClassificationCode" codeListValue="{fme:get-attribute("classification")}"/>
      			</gmd:classification>

      				</gmd:MD_SecurityConstraints>
      	</gmd:resourceConstraints>
      			<gmd:spatialRepresentationType>
      				<gmd:MD_SpatialRepresentationTypeCode codeListValue="{fme:get-attribute("spatialRepresentationType")}" codeList="http://standards.iso.org/ittf/PubliclyAvailableStandards/ISO_19139_Schemas/resources/Codelist/ML_gmxCodelists.xml#MD_SpatialRepresentationTypeCode"/>
      			</gmd:spatialRepresentationType>

      			{fme:process-features("DENOMINATOR")}
                  {fme:process-features("DISTANCE")}



      			<gmd:language>
      				<gco:CharacterString>{fme:get-attribute("language")}</gco:CharacterString>
      			</gmd:language>
      			<gmd:characterSet>
      				<gmd:MD_CharacterSetCode codeListValue="{fme:get-attribute("characterSet")}" codeList="http://standards.iso.org/ittf/PubliclyAvailableStandards/ISO_19139_Schemas/resources/Codelist/ML_gmxCodelists.xml#MD_CharacterSetCode"/>
      			</gmd:characterSet>

      			{fme:process-features("ISO")}

      			<gmd:extent>
      				<gmd:EX_Extent>
      					<gmd:description>
      						<gco:CharacterString>{fme:get-attribute("spatialDescription")}</gco:CharacterString>
      					</gmd:description>
      					<gmd:geographicElement>
      						<gmd:EX_GeographicBoundingBox>
      							<gmd:westBoundLongitude>
      								<gco:Decimal>{fme:get-attribute("westBoundLongitude")}</gco:Decimal>
      							</gmd:westBoundLongitude>
      							<gmd:eastBoundLongitude>
      								<gco:Decimal>{fme:get-attribute("eastBoundLongitude")}</gco:Decimal>
      							</gmd:eastBoundLongitude>
      							<gmd:southBoundLatitude>
      								<gco:Decimal>{fme:get-attribute("southBoundLatitude")}</gco:Decimal>
      							</gmd:southBoundLatitude>
      							<gmd:northBoundLatitude>
      								<gco:Decimal>{fme:get-attribute("northBoundLatitude")}</gco:Decimal>
      							</gmd:northBoundLatitude>
      						</gmd:EX_GeographicBoundingBox>
      					</gmd:geographicElement>
      				</gmd:EX_Extent>
      			</gmd:extent>

          <gmd:extent>
              <gmd:EX_Extent>

                  <gmd:temporalElement>

                      <gmd:EX_TemporalExtent>

                          <gmd:extent>

                             <gml:TimePeriod gml:id="T1">

                                  <gml:beginPosition>{fme:get-attribute("beginPosition")}</gml:beginPosition>
                                  <gml:endPosition>{fme:get-attribute("endPosition")}</gml:endPosition>

                              </gml:TimePeriod>

                          </gmd:extent>

                      </gmd:EX_TemporalExtent>

                  </gmd:temporalElement>

              </gmd:EX_Extent>

          </gmd:extent>


      		</gmd:MD_DataIdentification>
      	</gmd:identificationInfo>


           <gmd:distributionInfo>
           <gmd:MD_Distribution>
      {fme:process-features("DISTRIBUTION_ONLINE")}
      {fme:process-features("DISTRIBUTIONOFFLINE")}
      {fme:process-features("DISTRIBUTIONACCESLIMITEDOC")}
          </gmd:MD_Distribution>
          </gmd:distributionInfo>

      	<gmd:dataQualityInfo>
      		<gmd:DQ_DataQuality>
      			<gmd:scope>
      				<gmd:DQ_Scope>
      					<gmd:level>
      						<gmd:MD_ScopeCode codeList="http://standards.iso.org/ittf/PubliclyAvailableStandards/ISO_19139_Schemas/resources/Codelist/ML_gmxCodelists.xml#MD_ScopeCode" codeListValue="{fme:get-attribute("level")}"/>
      					</gmd:level>
      				</gmd:DQ_Scope>
      			</gmd:scope>

              <gmd:report>
      				<gmd:DQ_DomainConsistency>
      					<gmd:result>
      						<gmd:DQ_ConformanceResult>
      						<gmd:specification>
      					<gmd:CI_Citation>
      						<gmd:title>
      							<gco:CharacterString>Règlement (UE) n o 1089/2010 de la Commission du 23 novembre 2010 portant modalités d'application de la directive 2007/2/CE du Parlement européen et du Conseil en ce qui concerne l'interopérabilité des séries et des services de données géographiques</gco:CharacterString>
      						</gmd:title>
      						<gmd:date>
      							<gmd:CI_Date>
      								<gmd:date>
      									<gco:Date>2010-12-08</gco:Date>
      								</gmd:date>
      								<gmd:dateType>
      									<gmd:CI_DateTypeCode codeList="http://standards.iso.org/ittf/PubliclyAvailableStandards/ISO_19139_Schemas/resources/Codelist/ML_gmxCodelists.xml#CI_DateTypeCode" codeListValue="publication">publication</gmd:CI_DateTypeCode>
      								</gmd:dateType>
      							</gmd:CI_Date>
      						</gmd:date>
      					</gmd:CI_Citation>
      				</gmd:specification>
      				<gmd:explanation>
      					<gco:CharacterString></gco:CharacterString>
      				</gmd:explanation>
      						{fme:process-features("CONFORMANCEPASS_EVALUEE")}
                              {fme:process-features("CONFORMANCEPASS_PASEVALUEE")}
      						</gmd:DQ_ConformanceResult>
      					</gmd:result>
      				</gmd:DQ_DomainConsistency>

      			</gmd:report>
            {fme:process-features("CONFORMITE_INSPIRE")}
      			<gmd:lineage>
      				<rw:LI_Lineage gco:isoType="gmd:LI_Lineage">
      					<gmd:statement>
      						<gco:CharacterString>{fme:get-attribute("statementLineage")}</gco:CharacterString>
      					</gmd:statement>
      				</rw:LI_Lineage>
      			</gmd:lineage>
      		</gmd:DQ_DataQuality>
      	</gmd:dataQualityInfo>
      </rw:MD_Metadata>
    DISTRIBUTIONACCESLIMITEDOC_QUERY_EXPR:
                  <gmd:transferOptions>
      				<gmd:MD_DigitalTransferOptions>
      					<gmd:onLine>
      						<gmd:CI_OnlineResource>
      							<gmd:linkage>
      								<gmd:URL>{fme:get-attribute("Distributionacceslimite_dirstributionURLApp")}</gmd:URL>
      							</gmd:linkage>
      							<gmd:protocol gco:nilReason="missing">
      								<gco:CharacterString>{fme:get-attribute("Distributionacceslimite_distributionProtocolApp")}</gco:CharacterString>
      							</gmd:protocol>
      							<gmd:name>
      								<gco:CharacterString>{fme:get-attribute("Distributionacceslimite_distributionNameApp")}</gco:CharacterString>
      							</gmd:name>
      							<gmd:description>
      								<gco:CharacterString>{fme:get-attribute("Distributionacceslimite_distributionDescriptioApp")}</gco:CharacterString>
      							</gmd:description>
                                  <gmd:function>
      								<gmd:CI_OnLineFunctionCode codeList="http://standards.iso.org/ittf/PubliclyAvailableStandards/ISO_19139_Schemas/resources/Codelist/ML_gmxCodelists.xml#CI_OnLineFunctionCode" codeListValue="{fme:get-attribute("Distributionacceslimite_distributionFunctioApp")}"/>
      							</gmd:function>
      						</gmd:CI_OnlineResource>
      					</gmd:onLine>
      					</gmd:MD_DigitalTransferOptions>
      			</gmd:transferOptions>
    VISIBLE_QUERY_VALIDATE = Yes
    DISTRIBUTION_ONLINE_QUERY_EXPR:
      <gmd:distributor>
      				<gmd:MD_Distributor>
      					<gmd:distributorContact>
      						<gmd:CI_ResponsibleParty>
      							<gmd:organisationName>
      								<gco:CharacterString>{fme:get-attribute("Distributiononline_organisationName")}</gco:CharacterString>
      							</gmd:organisationName>
      							<gmd:contactInfo>
      								<gmd:CI_Contact>
      									<gmd:address>
      										<gmd:CI_Address>
      											<gmd:electronicMailAddress>
      												<gco:CharacterString>{fme:get-attribute("Distributiononline_electronicMailAddress")}</gco:CharacterString>
      											</gmd:electronicMailAddress>
      										</gmd:CI_Address>
      									</gmd:address>
      									<gmd:onlineResource>
      										<gmd:CI_OnlineResource>
      											<gmd:linkage>
      												<gmd:URL>{fme:get-attribute("Distributiononline_linkage")}</gmd:URL>
      											</gmd:linkage>
      											<gmd:protocol>
      												<gco:CharacterString>{fme:get-attribute("Distributiononline_protocole")}</gco:CharacterString>
      											</gmd:protocol>
      											<gmd:name>
      												<gco:CharacterString>{fme:get-attribute("Distributiononline_name")}</gco:CharacterString>
      											</gmd:name>
      											<gmd:description>
      												<gco:CharacterString>{fme:get-attribute("Distributiononline_description")}</gco:CharacterString>
      											</gmd:description>
      										</gmd:CI_OnlineResource>
      									</gmd:onlineResource>
      								</gmd:CI_Contact>
      							</gmd:contactInfo>
      							<gmd:role>
      								<gmd:CI_RoleCode codeList="http://standards.iso.org/ittf/PubliclyAvailableStandards/ISO_19139_Schemas/resources/Codelist/ML_gmxCodelists.xml#CI_RoleCode" codeListValue="distributor"/>
      							</gmd:role>
      						</gmd:CI_ResponsibleParty>
      					</gmd:distributorContact>
      					<gmd:distributionOrderProcess>
      						<gmd:MD_StandardOrderProcess>
      							<gmd:orderingInstructions>
      								<gco:CharacterString>{fme:get-attribute("Distributiononline_orderingInstructions1")}</gco:CharacterString>
      							</gmd:orderingInstructions>
      						</gmd:MD_StandardOrderProcess>
      					</gmd:distributionOrderProcess>
      					<gmd:distributorFormat>
      				<gmd:MD_Format>
      					<gmd:name>
      						<gco:CharacterString>{fme:get-attribute("Distributiononline_nameformat1")}</gco:CharacterString>
      					</gmd:name>
      					<gmd:version>
      						<gco:CharacterString>{fme:get-attribute("Distributiononline_versionFormat1")}</gco:CharacterString>
      					</gmd:version>
      				</gmd:MD_Format>
      			</gmd:distributorFormat>
      			<gmd:distributorTransferOptions>
      				<gmd:MD_DigitalTransferOptions>
      				<gmd:transferSize>
      				<gco:Real>{fme:get-attribute("Distributiononline_transfersize1 (créer bloc xml)")}</gco:Real>
      				</gmd:transferSize>
      				</gmd:MD_DigitalTransferOptions>

      			</gmd:distributorTransferOptions>
      			<gmd:distributorTransferOptions>
      				<gmd:MD_DigitalTransferOptions>
      					<gmd:onLine>
      							<gmd:CI_OnlineResource>
      									<gmd:linkage>
      										<gmd:URL>{fme:get-attribute("Distributiononline_dirstributionURLdl")}</gmd:URL>
      									</gmd:linkage>
      									<gmd:protocol>
      										<gco:CharacterString>{fme:get-attribute("Distributiononline_distributionProtocoldl")}</gco:CharacterString>
      									</gmd:protocol>
      									<gmd:name>
      										<gco:CharacterString>{fme:get-attribute("Distributiononline_distributionNamedl")}</gco:CharacterString>
      									</gmd:name>
      									<gmd:description>
      										<gco:CharacterString>{fme:get-attribute("Distributiononline_distributionDescriptiodl")}</gco:CharacterString>
      									</gmd:description>
      									<gmd:function>
      										<gmd:CI_OnLineFunctionCode codeList="http://standards.iso.org/ittf/PubliclyAvailableStandards/ISO_19139_Schemas/resources/Codelist/ML_gmxCodelists.xml#CI_OnLineFunctionCode" codeListValue="{fme:get-attribute("Distributiononline_distributionFunctiodl")}"/>
      									</gmd:function>
      								</gmd:CI_OnlineResource>
      					</gmd:onLine>
      				</gmd:MD_DigitalTransferOptions>
      			</gmd:distributorTransferOptions>



      				</gmd:MD_Distributor>
      			</gmd:distributor>
    MD_CONSTRAINTS_USELIMITATION_QUERY_EXPR:
      			<gmd:useLimitation>
      				<gco:CharacterString>{fme:get-attribute("uselimitations_MD_ConstraintsUselimitations")} </gco:CharacterString>
      			</gmd:useLimitation>
    DISTANCE_QUERY_EXPR:
          <gmd:spatialResolution>

              <gmd:MD_Resolution>

                  <gmd:distance>

                      <gco:Distance uom="m">{fme:get-attribute("Distance_Valeur")}</gco:Distance>

                  </gmd:distance>

              </gmd:MD_Resolution>

          </gmd:spatialResolution>
    DENOMINATOR_QUERY_EXPR:
      <gmd:spatialResolution>
      				<gmd:MD_Resolution>
      					<gmd:equivalentScale>
      						<gmd:MD_RepresentativeFraction>
      							<gmd:denominator>
      								<gco:Integer>{fme:get-attribute("Denominator_Valeur")}</gco:Integer>
      							</gmd:denominator>
      						</gmd:MD_RepresentativeFraction>
      					</gmd:equivalentScale>
      				</gmd:MD_Resolution>
      			</gmd:spatialResolution>
    USELIMITATION_QUERY_EXPR:
      <gmd:useLimitation>
      	<gco:CharacterString>{fme:get-attribute("uselimitationsValeur_comp")}</gco:CharacterString>
      </gmd:useLimitation>
    OUTPUT_XML_HEADER = Yes
    SYST_COORD_INSPIRE1_QUERY_EXPR:
      <gmd:referenceSystemInfo>
      		<gmd:MD_ReferenceSystem>
      			<gmd:referenceSystemIdentifier>
      				<gmd:RS_Identifier>
      					<gmd:code>
      						<gco:CharacterString>http://www.opengis.net/def/crs/EPSG/0/4258</gco:CharacterString>
      					</gmd:code>
      					<gmd:codeSpace>
      						<gco:CharacterString>urn:ogc:def:crs:EPSG</gco:CharacterString>
      					</gmd:codeSpace>
      				</gmd:RS_Identifier>
      			</gmd:referenceSystemIdentifier>
      		</gmd:MD_ReferenceSystem>
      	</gmd:referenceSystemInfo>
    CONFORMANCEPASS_PASEVALUEE_QUERY_EXPR = <gmd:pass gco:nilReason="unknown"> </gmd:pass>
    ISO_QUERY_EXPR:
      <gmd:topicCategory>
      				<gmd:MD_TopicCategoryCode>{fme:get-attribute("ISO_Valeur")}</gmd:MD_TopicCategoryCode>
      			</gmd:topicCategory>
    USECONSTRAINTS_QUERY_EXPR:
      	<gmd:useConstraints>
      		<gmd:MD_RestrictionCode codeList="http://standards.iso.org/ittf/PubliclyAvailableStandards/ISO_19139_Schemas/resources/Codelist/ML_gmxCodelists.xml#MD_RestrictionCode" codeListValue="{fme:get-attribute("uselimitationsUsecConstraints")}"/>
      	</gmd:useConstraints>
    OTHER_CONSTRAINTS_QUERY_EXPR:
      <gmd:otherConstraints>
      	<gco:CharacterString>{fme:get-attribute("regime_acces_ressourceOtherConstraints")}</gco:CharacterString>
      </gmd:otherConstraints>
    RESULT_ATTRIBUTE = _result
    CONFORMITE_INSPIRE_QUERY_EXPR:
            <gmd:report>
                  <gmd:DQ_DomainConsistency>
                     <gmd:measureIdentification>
                        <gmd:RS_Identifier>
                           <gmd:code gco:nilReason="missing">
                              <gco:CharacterString/>
                           </gmd:code>
                           <gmd:codeSpace gco:nilReason="missing">
                              <gco:CharacterString/>
                           </gmd:codeSpace>
                        </gmd:RS_Identifier>
                     </gmd:measureIdentification>
                     <gmd:measureDescription>
                        <gco:CharacterString>Conformité du jeu de données au modèle de données {fme:get-attribute("inspire_Nom")} d'INSPIRE</gco:CharacterString>
                     </gmd:measureDescription>
                     <gmd:dateTime gco:nilReason="missing"/>
                     <gmd:result>
                        <gmd:DQ_ConformanceResult>
                           <gmd:specification>
                              <gmd:CI_Citation>
                                 <gmd:title>
                                    <gco:CharacterString>{fme:get-attribute("inspire_Traduction")}</gco:CharacterString>
                                 </gmd:title>
                                 <gmd:date>
                                    <gmd:CI_Date>
                                       <gmd:date>
                                          <gco:Date>{fme:get-attribute("inspire_Date")}</gco:Date>
                                       </gmd:date>
                                       <gmd:dateType>
                                          <gmd:CI_DateTypeCode codeList="http://standards.iso.org/ittf/PubliclyAvailableStandards/ISO_19139_Schemas/resources/Codelist/ML_gmxCodelists.xml#CI_DateTypeCode"
                                                               codeListValue="publication"/>
                                       </gmd:dateType>
                                    </gmd:CI_Date>
                                 </gmd:date>
                              </gmd:CI_Citation>
                           </gmd:specification>
                           <gmd:explanation gco:nilReason="missing">
                              <gco:CharacterString/>
                           </gmd:explanation>
                           <gmd:pass><gco:Boolean>{fme:get-attribute("inspire_Conforme au thème")}</gco:Boolean></gmd:pass>
                        </gmd:DQ_ConformanceResult>
                     </gmd:result>
                  </gmd:DQ_DomainConsistency>
             </gmd:report>
    KEYWORDS_QUERY_EXPR:
                <gmd:descriptiveKeywords>
      				<gmd:MD_Keywords>
      					<gmd:keyword>
      						<gco:CharacterString>{fme:get-attribute("Keywords_Valeur")}</gco:CharacterString>
      					</gmd:keyword>
      					<gmd:type>
      						<gmd:MD_KeywordTypeCode codeList="http://standards.iso.org/ittf/PubliclyAvailableStandards/ISO_19139_Schemas/resources/Codelist/ML_gmxCodelists.xml#MD_KeywordTypeCode" codeListValue="theme"/>
      					</gmd:type>
      					<gmd:thesaurusName>
      						<gmd:CI_Citation>
      							<gmd:title>
      								<gco:CharacterString>{fme:get-attribute("Keywords_Nom")}</gco:CharacterString>
      							</gmd:title>
      							<gmd:date>
      								<gmd:CI_Date>
      									<gmd:date>
      										<gco:Date>{fme:get-attribute("Keywords_Date")}</gco:Date>
      									</gmd:date>
      									<gmd:dateType>
      										<gmd:CI_DateTypeCode codeList="http://standards.iso.org/ittf/PubliclyAvailableStandards/ISO_19139_Schemas/resources/Codelist/ML_gmxCodelists.xml#CI_DateTypeCode" codeListValue="{fme:get-attribute("Keywords_Type de date")}"/>
      									</gmd:dateType>
      								</gmd:CI_Date>
      							</gmd:date>
      						</gmd:CI_Citation>
      					</gmd:thesaurusName>
      				</gmd:MD_Keywords>
      			</gmd:descriptiveKeywords>
    LOCALCODE_QUERY_EXPR:
       <gmd:identifier>
           <gmd:MD_Identifier>
                  <gmd:code>
                      <gco:CharacterString>{fme:get-attribute("local_codeValeur1")}</gco:CharacterString>
                  </gmd:code>
            </gmd:MD_Identifier>
       </gmd:identifier>
    DISTRIBUTIONOFFLINE_QUERY_EXPR:
      <gmd:distributor>
      				<gmd:MD_Distributor>
      					<gmd:distributorContact>
      						<gmd:CI_ResponsibleParty>
      							<gmd:organisationName>
      								<gco:CharacterString>{fme:get-attribute("DistributionOffLine_organisationName")}</gco:CharacterString>
      							</gmd:organisationName>
      							<gmd:contactInfo>
      								<gmd:CI_Contact>
      									<gmd:address>
      										<gmd:CI_Address>
      											<gmd:electronicMailAddress>
      												<gco:CharacterString>{fme:get-attribute("DistributionOffLine_electronicMailAddress")}</gco:CharacterString>
      											</gmd:electronicMailAddress>
      										</gmd:CI_Address>
      									</gmd:address>
      									<gmd:onlineResource>
      										<gmd:CI_OnlineResource>
      											<gmd:linkage>
      												<gmd:URL>{fme:get-attribute("DistributionOffLine_linkage")}</gmd:URL>
      											</gmd:linkage>
      											<gmd:protocol>
      												<gco:CharacterString>{fme:get-attribute("DistributionOffLine_protocole")}</gco:CharacterString>
      											</gmd:protocol>
      											<gmd:name>
      												<gco:CharacterString>{fme:get-attribute("DistributionOffLine_name")}</gco:CharacterString>
      											</gmd:name>
      											<gmd:description>
      												<gco:CharacterString>{fme:get-attribute("DistributionOffLine_description")}</gco:CharacterString>
      											</gmd:description>
      										</gmd:CI_OnlineResource>
      									</gmd:onlineResource>
      								</gmd:CI_Contact>
      							</gmd:contactInfo>
      							<gmd:role>
      								<gmd:CI_RoleCode codeList="http://standards.iso.org/ittf/PubliclyAvailableStandards/ISO_19139_Schemas/resources/Codelist/ML_gmxCodelists.xml#CI_RoleCode" codeListValue="distributor"/>
      							</gmd:role>
      						</gmd:CI_ResponsibleParty>
      					</gmd:distributorContact>
      					<gmd:distributionOrderProcess>
      						<gmd:MD_StandardOrderProcess>
      							<gmd:orderingInstructions>
      								<gco:CharacterString>{fme:get-attribute("DistributionOffLine_orderingInstructions3")}</gco:CharacterString>
      							</gmd:orderingInstructions>
      						</gmd:MD_StandardOrderProcess>
      					</gmd:distributionOrderProcess>
      					<gmd:distributorFormat>
      				<gmd:MD_Format>
      					<gmd:name>
      						<gco:CharacterString>{fme:get-attribute("DistributionOffLine_nameformat3")}</gco:CharacterString>
      					</gmd:name>
      					<gmd:version>
      						<gco:CharacterString>{fme:get-attribute("DistributionOffLine_versionFormat3")}</gco:CharacterString>
      					</gmd:version>
      				</gmd:MD_Format>
      			</gmd:distributorFormat>
      			<gmd:distributorTransferOptions>
      				<gmd:MD_DigitalTransferOptions>
      				<gmd:transferSize>
      				<gco:Real>{fme:get-attribute("DistributionOffLine_transfersize3 (créer bloc xml)")}</gco:Real>
      				</gmd:transferSize>
      				</gmd:MD_DigitalTransferOptions>

      			</gmd:distributorTransferOptions>
      			<gmd:distributorTransferOptions>
      				<gmd:MD_DigitalTransferOptions>
      					<gmd:offLine>
      				<gmd:MD_Medium>
      					<gmd:name>
      						<gmd:MD_MediumNameCode codeList=" http://standards.iso.org/ittf/PubliclyAvailableStandards/ISO_19139_Schemas/resources/codelist/gmxCodelists.xml#MD_MediumNameCode" codeListValue="{fme:get-attribute("DistributionOffLine_mediumNameCode")}"/>
      					</gmd:name>
      					<gmd:mediumNote>
      						<gco:CharacterString>{fme:get-attribute("DistributionOffLine_mediumName")}</gco:CharacterString>
      					</gmd:mediumNote>
      				</gmd:MD_Medium>
      			</gmd:offLine>
      				</gmd:MD_DigitalTransferOptions>
      			</gmd:distributorTransferOptions>



      				</gmd:MD_Distributor>
      			</gmd:distributor>
    CONTACT_QUERY_EXPR:
                          <gmd:pointOfContact>
                      <rw:CI_ResponsibleParty gco:isoType="gmd:CI_ResponsibleParty">
      					<gmd:individualName>
      						<gco:CharacterString>{fme:get-attribute("Contactsupp_individualName")}</gco:CharacterString>
      					</gmd:individualName>
      					<gmd:organisationName>
      						<gco:CharacterString>{fme:get-attribute("Contactsupp_organisationName")}</gco:CharacterString>
      					</gmd:organisationName>
      					<gmd:contactInfo>
      						<gmd:CI_Contact>
      							<gmd:phone>
      								<gmd:CI_Telephone>
      									<gmd:voice>
      										<gco:CharacterString>{fme:get-attribute("Contactsupp_voice")}</gco:CharacterString>
      									</gmd:voice>
      									<gmd:facsimile>
      										<gco:CharacterString></gco:CharacterString>
      									</gmd:facsimile>
      								</gmd:CI_Telephone>
      							</gmd:phone>
      							<gmd:address>
      								<gmd:CI_Address>
      									<gmd:deliveryPoint>
      										<gco:CharacterString></gco:CharacterString>
      									</gmd:deliveryPoint>
      									<gmd:deliveryPoint>
      										<gco:CharacterString></gco:CharacterString>
      									</gmd:deliveryPoint>
      									<gmd:deliveryPoint>
      										<gco:CharacterString>{fme:get-attribute("Contactsupp_deliveryPoint")}</gco:CharacterString>
      									</gmd:deliveryPoint>
      									<gmd:city>
      										<gco:CharacterString>{fme:get-attribute("Contactsupp_city")}</gco:CharacterString>
      									</gmd:city>
      									<gmd:postalCode>
      										<gco:CharacterString>{fme:get-attribute("Contactsupp_postalCode")}</gco:CharacterString>
      									</gmd:postalCode>
      									<gmd:country>
      										<gco:CharacterString>{fme:get-attribute("Contactsupp_country")}</gco:CharacterString>
      									</gmd:country>
      									<gmd:electronicMailAddress>
      										<gco:CharacterString>{fme:get-attribute("Contactsupp_electronicMailAddress")}</gco:CharacterString>
      									</gmd:electronicMailAddress>
      								</gmd:CI_Address>
      							</gmd:address>
      							<gmd:onlineResource>
      								<gmd:CI_OnlineResource>
      									<gmd:linkage>
      										<gmd:URL>{fme:get-attribute("Contactsupp_linkage")}</gmd:URL>
      									</gmd:linkage>
      									<gmd:protocol>
      										<gco:CharacterString>{fme:get-attribute("Contactsupp_protocole")}</gco:CharacterString>
      									</gmd:protocol>
      									<gmd:name>
      										<gco:CharacterString>{fme:get-attribute("Contactsupp_name")}</gco:CharacterString>
      									</gmd:name>
      									<gmd:description>
      										<gco:CharacterString>{fme:get-attribute("Contactsupp_description")}</gco:CharacterString>
      									</gmd:description>
      									<gmd:function>
      										<gmd:CI_OnLineFunctionCode codeList="http://standards.iso.org/ittf/PubliclyAvailableStandards/ISO_19139_Schemas/resources/Codelist/ML_gmxCodelists.xml#CI_OnLineFunctionCode" codeListValue="{fme:get-attribute("Contactsupp_function")}"/>
      									</gmd:function>
      								</gmd:CI_OnlineResource>
      							</gmd:onlineResource>
      						</gmd:CI_Contact>
      					</gmd:contactInfo>
      					<gmd:role>
      						<gmd:CI_RoleCode codeList="http://standards.iso.org/ittf/PubliclyAvailableStandards/ISO_19139_Schemas/resources/Codelist/ML_gmxCodelists.xml#CI_RoleCode" codeListValue="{fme:get-attribute("Contactsupp_Role")}"/>
      					</gmd:role>
      					<rw:responsiblePartyLanguage>
      						<gmd:LanguageCode codeList="http://www.loc.gov/standards/iso639-2/" codeListValue="fre"/>
      					</rw:responsiblePartyLanguage>
      				</rw:CI_ResponsibleParty>
                          </gmd:pointOfContact>
    CONTACT_METADATA_QUERY_EXPR:
      	<gmd:contact>
      		<rw:CI_ResponsibleParty gco:isoType="gmd:CI_ResponsibleParty">
      			<gmd:individualName>
      				<gco:CharacterString>{fme:get-attribute("ContactMetadata_individualName")}</gco:CharacterString>
      			</gmd:individualName>
      			<gmd:organisationName>
      				<gco:CharacterString>{fme:get-attribute("ContactMetadata_organisationName")}</gco:CharacterString>
      			</gmd:organisationName>
      			<gmd:positionName gco:nilReason="">
      				<gco:CharacterString>{fme:get-attribute("ContactMetadata_positionName")}</gco:CharacterString>
      			</gmd:positionName>
      			<gmd:contactInfo>
      				<gmd:CI_Contact>
      					<gmd:phone>
      						<gmd:CI_Telephone>
      							<gmd:voice>
      								<gco:CharacterString>{fme:get-attribute("ContactMetadata_voice")}</gco:CharacterString>
      							</gmd:voice>
      							<gmd:facsimile>
      								<gco:CharacterString></gco:CharacterString>
      							</gmd:facsimile>
      						</gmd:CI_Telephone>
      					</gmd:phone>
      					<gmd:address>
      						<gmd:CI_Address>
      							<gmd:deliveryPoint>
      								<gco:CharacterString></gco:CharacterString>
      							</gmd:deliveryPoint>
      							<gmd:deliveryPoint>
      								<gco:CharacterString></gco:CharacterString>
      							</gmd:deliveryPoint>
      							<gmd:deliveryPoint>
      								<gco:CharacterString>{fme:get-attribute("ContactMetadata_deliveryPoint")}</gco:CharacterString>
      							</gmd:deliveryPoint>
      							<gmd:city>
      								<gco:CharacterString>{fme:get-attribute("ContactMetadata_city")}</gco:CharacterString>
      							</gmd:city>
      							<gmd:postalCode>
      								<gco:CharacterString>{fme:get-attribute("ContactMetadata_postalCode")}</gco:CharacterString>
      							</gmd:postalCode>
      							<gmd:country>
      								<gco:CharacterString>{fme:get-attribute("ContactMetadata_country")}</gco:CharacterString>
      							</gmd:country>
      							<gmd:electronicMailAddress>
      								<gco:CharacterString>{fme:get-attribute("ContactMetadata_electronicMailAddress")}</gco:CharacterString>
      							</gmd:electronicMailAddress>
      						</gmd:CI_Address>
      					</gmd:address>
      					<gmd:onlineResource>
      						<gmd:CI_OnlineResource>
      							<gmd:linkage>
      								<gmd:URL>{fme:get-attribute("ContactMetadata_linkage")}</gmd:URL>
      							</gmd:linkage>
      							<gmd:protocol>
      								<gco:CharacterString>{fme:get-attribute("ContactMetadata_protocole")}</gco:CharacterString>
      							</gmd:protocol>
      							<gmd:name>
      								<gco:CharacterString>{fme:get-attribute("ContactMetadata_name")}</gco:CharacterString>
      							</gmd:name>
      							<gmd:description>
      								<gco:CharacterString>{fme:get-attribute("ContactMetadata_description")}</gco:CharacterString>
      							</gmd:description>
      							<gmd:function>
      								<gmd:CI_OnLineFunctionCode codeList="http://standards.iso.org/ittf/PubliclyAvailableStandards/ISO_19139_Schemas/resources/Codelist/ML_gmxCodelists.xml#CI_OnLineFunctionCode" codeListValue="{fme:get-attribute("ContactMetadata_function")}"/>
      							</gmd:function>
      						</gmd:CI_OnlineResource>
      					</gmd:onlineResource>
      				</gmd:CI_Contact>
      			</gmd:contactInfo>
      			<gmd:role>
      				<gmd:CI_RoleCode codeList="http://standards.iso.org/ittf/PubliclyAvailableStandards/ISO_19139_Schemas/resources/Codelist/ML_gmxCodelists.xml#CI_RoleCode" codeListValue="{fme:get-attribute("ContactMetadata_Role")}"/>
      			</gmd:role>
      			<rw:responsiblePartyLanguage>
      				<gmd:LanguageCode codeList="http://www.loc.gov/standards/iso639-2/" codeListValue="{fme:get-attribute("ContactMetadata_metadata_lang")}"/>
      			</rw:responsiblePartyLanguage>
      		</rw:CI_ResponsibleParty>
      	</gmd:contact>
    HIERARCHYLEVEL_QUERY_EXPR:
          <gmd:hierarchyLevelName>

              <gco:CharacterString>{fme:get-attribute("hierarchylevel_Valeur")}</gco:CharacterString>

          </gmd:hierarchyLevelName>
    ACCESS_CONSTRAINT_QUERY_EXPR:
      <gmd:accessConstraints>
      				<gmd:MD_RestrictionCode codeList="http://standards.iso.org/ittf/PubliclyAvailableStandards/ISO_19139_Schemas/resources/Codelist/ML_gmxCodelists.xml#MD_RestrictionCode" codeListValue="{fme:get-attribute("regime_acces_ressourceAccessConstraints")}"/>
      </gmd:accessConstraints>
    KEYWORDS_FREE_QUERY_EXPR:
      <gmd:descriptiveKeywords>
      				<gmd:MD_Keywords>
      				<gmd:keyword><gco:CharacterString>{fme:get-attribute("Keywordsfree_Valeur")}</gco:CharacterString></gmd:keyword>

      				</gmd:MD_Keywords>
      			</gmd:descriptiveKeywords>
    -> text_line (writer TEXTLINE_1)
text_line (writer TEXTLINE_1)
    attributes: text_line_data buffer
