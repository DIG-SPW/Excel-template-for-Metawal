FME workspace DGO4_2.fmw

Parameters:
- Dossier_traitement = C:\Users\elise\Desktop\traitement
- Description =
- nom_data =
- theme =
- nom =
- tel =
- mail =
- Fichier_source_excel =
- abreg_data =
- maj =
- DestDataset_XLSXW = C:\Users\elise\Desktop\fichier. xlsm   # Destination Microsoft Excel File
- Nom_fichier = fichier.xlsx   # Nom_Fichier

Writers:
- XLSXW_1: XLSXW to $(DestDataset_XLSXW)

Creator
    NUM = 1
    GEOMTYPE = Geometry Object
    CREATED -> ParameterFetcher
ParameterFetcher
    ATTR_LIST = Description {$(Description)} nom_data {$(nom_data)} theme {$(theme)} nom {$(nom)} tel {$(tel)} mail {$(mail)} Dossier_traitement {$(Dossier_traitement)} abreg_data {$(abreg_data)} maj {$(maj)}
    -> FilenamePartExtractor
FilenamePartExtractor
    SRC_ATTR = $(Fichier_source_excel)
    FULLNAME_ATTR = _filename
    -> AttributeCreator
AttributeCreator
    ATTR_LIST = Nom_fichier,@Value(abreg_data).xlsm
    -> AttributeCreator_2
AttributeCreator_2
    ATTR_LIST:
      contenu,cd @Value(Dossier_traitement)
      rename @Value(_filename) @Value(Nom_fichier),Nom_fichier_data,@Value(abreg_data)_data
    -> PythonCaller
PythonCaller
    PYTHONSOURCE:
      import fmeobjects
      import os
      import shutil


      # Template Function interface:
      def traitement(feature):
         Nom_Fichier_sortie=feature.getAttribute("fichier_dataset")
         Fichier_source=FME_MacroValues['Fichier_source_excel']
         Fichier_source_nom=feature.getAttribute("_filename")
         contenu=feature.getAttribute("contenu")
         Dossier_traitement=FME_MacroValues['Dossier_traitement']
         shutil.copy(Fichier_source,Dossier_traitement)
         os.chdir(Dossier_traitement)
         file = open("fichier.bat", "w")
         file.write(contenu)
         file.close()
         os.system("fichier.bat")
         os.remove("fichier.bat")
    PYTHONSYMBOL = traitement
    -> data_move (writer XLSXW_1)
data_move (writer XLSXW_1)
    attributes: nom_data string(20,format_type;Simple;font_type;;font_color;;fill_color;;custom_options;<Unused>), theme string(20,format_type;Simple;font_type;;font_color;;fill_color;;custom_options;;text_wrap;no), Description string(20,format_type;Simple;font_type;;font_color;;fill_color;;custom_options;;text_wrap;no), nom string(20,format_type;Simple;font_type;;font_color;;fill_color;;custom_options;;text_wrap;no), tel string(20,format_type;Simple;font_type;;font_color;;fill_color;;custom_options;;text_wrap;no), mail string(20,format_type;Simple;font_type;;font_color;;fill_color;;custom_options;;text_wrap;no), maj string(20,format_type;Simple;font_type;;font_color;;fill_color;;custom_options;;text_wrap;no)
