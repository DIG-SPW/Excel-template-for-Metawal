FME workspace DGO3_1.fmw

Parameters:
- fichier_source_excel = H:\gimb14\c\c130606\data\templates\Fiche_encodage_complete_master.xlsm   # Fichier Template fichier excel
- Dossier_traitement = C:\Users\elise\Desktop\traitement   # Dossier_enregistrement_fichier_output
- SourceDataset_MDB_ADO = H:\gimb14\c\c130606\data\DGO3\Extrait_TB_1.mdb   # MDB

Readers:
- MDB_ADO_1: MDB_ADO from $(SourceDataset_MDB_ADO)

DATA (reader MDB_ADO_1)
    attributes: ID_Data autonumber, abreg_data text(50), nom_data text(255), theme long, Description memo, Imagette text(50), categ_avancement text(150), Metadata_YN yesno, pers_encodage_gene text(50), date_encodage_gene datetime, org_auteur long, org_proprio long, pers_data long, pers_matière long, localisation text(255), pers_encodage_DGRNE text(50), date_encodage_DGRNE datetime, date_version_DGRNE text(50), sauvegarde_DGRNE text(100), remarque_DGRNE memo, info_version_DGRNE memo, proc_màj_DGRNE memo, DGRNE_internet text(50), DGRNE_obtention memo, DGRNE_dico yesno, DGRNE_OGEAD yesno, DGRNE_OGEAD_intra yesno, DGRNE_OGEAD_REMARQUE memo, DGRNE_path_lyr text(255), pers_encodage_DGATLP text(50),
      date_encodage_DGATLP datetime, date_version_DGATLP text(50), sauvegarde_DGATLP text(100), remarque_DGATLP memo, info_version_DGATLP memo, proc_màj_DGATLP memo, DGATLP_internet text(50), DGATLP_obtention memo, DGATLP_description memo, DGATLP_path_lyr text(255), DGATLP_copyright integer
    -> AttributeKeeper
AttributeKeeper
    KEEP_ATTRS = abreg_data,nom_data,theme,Description,pers_matière
    -> ParameterFetcher
ParameterFetcher
    ATTR_LIST = Dossier_traitement {$(Dossier_traitement)}
    -> AttributeCreator_2
AttributeCreator_2
    ATTR_LIST = Nom_fichier,@Value(abreg_data).xlsm,Nom_fichier_data,@Value(abreg_data)_data,nom_fichier_data_xlsx,$(Dossier_traitement)\@Value(abreg_data)_data.xlsx
    -> AttributeCreator_3
AttributeCreator_3
    ATTR_LIST:
      fichier_vbs,Dim objExcel
          Dim objWB1
          Dim objWB2
          Dim ws
          Set objExcel = CreateObject("Excel.Application")
          objExcel.DisplayAlerts = False
          Set objWB1 = objExcel.Workbooks.Open("@Value(Dossier_traitement)\@Value(Nom_fichier_data).xlsx")
      	Set objWB2 = objExcel.Workbooks.Open("@Value(Dossier_traitement)\@Value(Nom_fichier)")

          objWB2.Unprotect "GIMPRO"

          For Each ws In objWB1.Sheets
              ws.Copy objWB2.Sheets(objWB2.Sheets.Count)
          Next
          objWB1.Close False
          objWB2.Save
          objWB2.Close
          With objExcel

              .DisplayAlerts = True
              .Quit
          End With

      ' Open the workbook
      	Set objWorkbook = objExcel.Workbooks.Open ("@Value(Dossier_traitement)\@Value(Nom_fichier)")

      	objExcel.Visible = False

         Set c=objWorkbook.Worksheets("data_move")

      	c.Range("E2").Copy
      	objWorkbook.Worksheets("Contacts").Range("H6").PasteSpecial -4163


          c.Range("G2").Copy
      	objWorkbook.Worksheets("Contacts").Range("H5").PasteSpecial -4163


          c.Range("F2").Copy
      	objWorkbook.Worksheets("Contacts").Range("H8").PasteSpecial -4163

          c.Range("D2").Copy
      	objWorkbook.Worksheets("Description").Range("G5").PasteSpecial -4163

          c.Range("C2").Copy
      	objWorkbook.Worksheets("Description").Range("G15").PasteSpecial -4163

           c.Range("A2").Copy
      	objWorkbook.Worksheets("Identification").Range("F3").PasteSpecial -4163

          c.Range("B2").Copy
      	objWorkbook.Worksheets("Identification").Range("F5").PasteSpecial -4163

      	objWorkbook.Save

          objExcel.DisplayAlerts = False
      	objWorkbook.sheets("data_move").Delete
          objWorkbook.sheets("Accueil-Instructions").Select
          objExcel.DisplayAlerts = True
      	objWorkbook.Protect "GIMPRO"

      objWorkbook.Save
      objExcel.Quit
    -> WorkspaceRunner_2
WorkspaceRunner_2
    WORKSPACE_FILE = $(FME_MF_DIR)DGO3_2.fmw
    BLOCKING = Yes
    WORKSPACE_PARAMETERS = Dossier_traitement,$(Dossier_traitement),Fichier_source,$(fichier_source_excel),SourceDataset_MDB_ADO,$(SourceDataset_MDB_ADO),abreg_data,@Value(abreg_data),Description,@Value(Description),nom_data,@Value(nom_data),pers_matière,@Value(pers_matière),theme,@Value(theme)
    SUCCEEDED -> PythonCaller
    FAILED -> WorkspaceRunner_Failed
PythonCaller
    PYTHONSOURCE:
      import fmeobjects
      import os


      # Template Function interface:
      def traitement(feature):
         fichier_vbs=feature.getAttribute("fichier_vbs")
         Nom=feature.getAttribute("nom_fichier_data_xlsx")
         Dossier_traitement=FME_MacroValues['Dossier_traitement']
         os.chdir(Dossier_traitement)
         file = open("fichier.vbs", "w")
         file.write(fichier_vbs)
         file.close()
         os.system("fichier.vbs")
         os.remove("fichier.vbs")
         os.remove(Nom)
    PYTHONSYMBOL = traitement
WorkspaceRunner_Failed: Inspector
