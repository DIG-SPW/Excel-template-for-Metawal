FME workspace DGO4_1.fmw

Parameters:
- Dossier_traitement = C:\Users\elise\Desktop\traitement   # Localisation fichiers output
- fichier_source_excel = H:\gimb14\c\c130606\data\templates\Fiche_encodage_complete_master.xlsm   # excel template excel
- SourceDataset_XLSXR = H:\gimb14\c\c130606\data\DGO4\DATASETS.xlsx   # Fichier excel Datasets
- SourceDataset_XLSXR_5 = H:\gimb14\c\c130606\data\DGO4\COUCHES.xlsx   # Fichier excel Couches
- SourceDataset_XLSXR_4 = H:\gimb14\c\c130606\data\DGO4\Requête1.xlsx   # Fichier excel Requête1

Readers:
- XLSXR_1: XLSXR from $(SourceDataset_XLSXR)
- XLSXR_2: XLSXR from $(SourceDataset_XLSXR_5)
- XLSXR_3: XLSXR from $(SourceDataset_XLSXR_4)

EXPORT_DATA (reader XLSXR_1)
    attributes: nom_data char(179), theme char(101), Description char(1708), categ_avancement number(2,0), _Auteur : _ char(47), _Auteur DG : _ char(5), _Auteur D :_ char(5), _Auteur di : _ char(11), _Propriétaire  : _ char(4), _Propriétaire DG : _ char(15), _Propriétaire D : _ char(19), _Propriétaire di: _ char(11), Gestionnaire : nom char(13), Gestionnaire : prenom char(16), Gestionnaire : tel char(16), Gestionnaire : mail char(38), localisation char(42), info_version_DGATLP char(437), proc_màj_DGATLP char(37), DGATLP_internet char(18), DGATLP_obtention char(459), DGATLP_description char(440), DGATLP_copyright number(2,0)
    -> AttributeKeeper
AttributeKeeper
    KEEP_ATTRS = nom_data,theme,Description,"Gestionnaire : nom","Gestionnaire : prenom","Gestionnaire : tel","Gestionnaire : mail",DGATLP_internet,abreg_data
    -> Tester
Tester
    TEST_MODE = Automatic
    TEST_DESCRIPTION = ""
    BOOL_OP = OR
    TEST_CLAUSE = TEST @Value(DGATLP_internet) = Internet
    PASSED -> FeatureMerger [input 1]
Requête1 (reader XLSXR_3)
    attributes: abreg_data char(11), DATA_nom_data char(91), abreg_couche char(25), nom_explicite char(96), EXPORT_DATA_nom_data char(91)
    -> AttributeKeeper_2
AttributeKeeper_2
    KEEP_ATTRS = abreg_data,DATA_nom_data,abreg_couche
    -> FeatureMerger [input 2]
FeatureMerger
    PROCESS_DUPS = No
    MERGE_TYPE = Attributes Only
    SUPPLIERS_FIRST = No
    JOIN_KEYS = @Value(nom_data) @Value(DATA_nom_data) AUTO
    SUPPLIER_PREFIX_DUMMY = YES
    MERGED -> FeatureMerger_2 [input 1]
COUCHES (reader XLSXR_2)
    attributes: abreg_couche char(25), nom_explicite char(96), abreg_data char(11), nom_fichier_DGATLP char(29), maj_DGATLP char(11)
    -> AttributeKeeper_3
AttributeKeeper_3
    KEEP_ATTRS = abreg_couche,abreg_data,maj_DGATLP
    -> FeatureMerger_2 [input 2]
FeatureMerger_2
    PROCESS_DUPS = No
    MERGE_TYPE = Attributes Only
    SUPPLIERS_FIRST = No
    JOIN_KEYS = @Value(abreg_couche) @Value(abreg_couche) AUTO
    SUPPLIER_PREFIX_DUMMY = YES
    MERGED -> DateFormatter
    NOT_MERGED -> AttributeCreator
DateFormatter
    DATE_ATTR = maj_DGATLP
    FMT = %Y-%m-%d
    SRCFMT = %d/%m/%Y
    INVALID_DATE_VALUE = _FME_NO_OP_
    -> ParameterFetcher
AttributeCreator
    ATTR_LIST = maj_DGATLP,""
    -> ParameterFetcher
ParameterFetcher
    ATTR_LIST = Dossier_traitement {$(Dossier_traitement)}
    -> AttributeCreator_2
AttributeCreator_2
    ATTR_LIST = Nom_fichier,@Value(abreg_data).xlsm,Nom_fichier_data,@Value(abreg_data)_data,nom_fichier_data_xlsx,$(Dossier_traitement)\@Value(abreg_data)_data.xlsx,nom,@Value(Gestionnaire : nom) @Value(Gestionnaire : prenom)
    -> AttributeCreator_3
AttributeCreator_3
    ATTR_LIST:
      fichier_vbs,Dim objExcel
          Dim objWB1
          Dim objWB2
          Dim ws
          Set objExcel = CreateObject("Excel.Application")
          objExcel.DisplayAlerts = False
          Set objWB1 = objExcel.Workbooks.Open("@Value(Dossier_traitement)\@Value(Nom_fichier_data).xlsx")
      	Set objWB2 = objExcel.Workbooks.Open("@Value(Dossier_traitement)\@Value(Nom_fichier)")

           objWB2.Unprotect "GIMPRO"

          For Each ws In objWB1.Sheets
              ws.Copy objWB2.Sheets(objWB2.Sheets.Count)
          Next
          objWB1.Close False
          objWB2.Save
          objWB2.Close
          With objExcel

              .DisplayAlerts = True
              .Quit
          End With

      ' Open the workbook
      	Set objWorkbook = objExcel.Workbooks.Open ("@Value(Dossier_traitement)\@Value(Nom_fichier)")

      	objExcel.Visible = False

         Set c=objWorkbook.Worksheets("data_move")

      	    c.Range("A2").Copy
      	objWorkbook.Worksheets("Identification").Range("F3").PasteSpecial -4163


              c.Range("B2").Copy
      	objWorkbook.Worksheets("Description").Range("G15").PasteSpecial -4163

            c.Range("C2").Copy
      	objWorkbook.Worksheets("Description").Range("G5").PasteSpecial -4163

          c.Range("D2").Copy
      	objWorkbook.Worksheets("Contacts").Range("H6").PasteSpecial -4163


          c.Range("E2").Copy
      	objWorkbook.Worksheets("Contacts").Range("H8").PasteSpecial -4163

          c.Range("F2").Copy
      	objWorkbook.Worksheets("Contacts").Range("H5").PasteSpecial -4163

             c.Range("G2").Copy
      	objWorkbook.Worksheets("Description").Range("G19").PasteSpecial -4163





      	objWorkbook.Save

          objExcel.DisplayAlerts = False
      	objWorkbook.sheets("data_move").Delete
          objWorkbook.sheets("Accueil-Instructions").Select
          objExcel.DisplayAlerts = True
      	objWorkbook.Protect "GIMPRO"

      objWorkbook.Save
      objExcel.Quit
    -> WorkspaceRunner
WorkspaceRunner
    WORKSPACE_FILE = DGO4_2.fmw
    BLOCKING = Yes
    WORKSPACE_PARAMETERS = Dossier_traitement,$(Dossier_traitement),Description,@Value(Description),nom_data,@Value(nom_data),theme,@Value(theme),nom,@Value(Gestionnaire : nom),tel,@Value(Gestionnaire : tel),mail,@Value(Gestionnaire : mail),Fichier_source_excel,$(fichier_source_excel),abreg_data,@Value(abreg_data),maj,@Value(maj_DGATLP)
    SUCCEEDED -> PythonCaller
    FAILED -> WorkspaceRunner_Failed
PythonCaller
    PYTHONSOURCE:
      import fmeobjects
      import os


      # Template Function interface:
      def traitement(feature):
         fichier_vbs=feature.getAttribute("fichier_vbs")
         Nom=feature.getAttribute("nom_fichier_data_xlsx")
         file = open("fichier.vbs", "w")
         file.write(fichier_vbs)
         file.close()
         os.system("fichier.vbs")
         os.remove("fichier.vbs")
         os.remove(Nom)
    PYTHONSYMBOL = traitement
WorkspaceRunner_Failed: Inspector
